Avaya-SparkIPTelephone-MIB 
--DEFAULT get-function-async SnmpManagerGet
--DEFAULT set-function-async null_set_async
--DEFAULT next-function-async SnmpManagerNext
--DEFAULT test-function-async null_test_async 
DEFINITIONS ::= BEGIN     
IMPORTS
            enterprises, OBJECT-TYPE, MODULE-IDENTITY, Integer32, IpAddress
                FROM SNMPv2-SMI 
        DisplayString 
        FROM RFC1213-MIB ;

avayaSparkMIB MODULE-IDENTITY
    LAST-UPDATED     "2103171400Z" --YYMMDDHHMM
             ORGANIZATION     "avaya"
             CONTACT-INFO     "Avaya Customer Services
                   Avaya, Inc.
                   4655 Great America Parkway
                   Santa Clara, CA 95054 USA
                   WWW: www.avaya.com
                   Tel: +1 908 953 6000"
        DESCRIPTION "MIB Module for Mercury SIP IP Telephones as of Release 4.0.9.0
            Copyright 2021 by Avaya Inc.  All rights reserved."    
            REVISION "1705251907Z" --YYMMDDHHMM
            DESCRIPTION 
                        "
						Version 4.0.9.0
							1. Add new parameters endptUSBSTICKMODEL
							2. Add new parameters endptUSBSTICKMANUFACTURER
							3. Add new parameters endptUSBSTICKSN
							4. Add new parameters endptUSBSTICKFW
							5. Add new parameters endptUSBKEYBOARDMODEL
							6. Add new parameters endptUSBKEYBOARDMANUFACTURER
							7. Add new parameters endptUSBKEYBOARDSN
							8. Add new parameters endptUSBKEYBOARDFW
							9. Add new parameters endptSHAREDLINE<n>SUBSCRIBETARGET
							10. Add new parameters endptENABLEUSBDEVICE
							11. Add new parameters endptENABLEUSBSTICK
							12. Add new parameters endptENABLEUSBKEYBOARD
							13. Modify parameter description endptSHAREDLINEMODE
							14. Modify parameter description endptSHAREDLINE<n>MAXCALLAPPEARANCES
							15. Modify parameter description endptSHAREDLINE<n>ENABLED
							16. Modify parameter description endptSHAREDLINE<n>SIPUSERID
							17. Modify parameter description endptSHAREDLINE<n>USERNAME
							18. Modify parameter description endptSHAREDLINE<n>EXTENSION
							19. Modify parameter description endptSHAREDLINE<n>BARGEINENABLED
							20. Modify parameter description endptSHAREDLINE<n>INCOMINGCALLINDICATIONDEFAULT
							21. Modify parameter description endptSHAREDLINE<n>INCOMINGCALLINDICATIONDELAYEDDEFAULT
                        Version 4.0.8.0
                            1. Add new parameters SOFTKEY_SCA_TRANSFER_DIALING, OVERRIDE_SOFTKEY_SCA_TRANSFER_DIALING
							2. Add new parameters SOFTKEY_SCA_TRANSFER_OUTGOING, OVERRIDE_SOFTKEY_SCA_TRANSFER_OUTGOING
							3. Add new parameters SOFTKEY_SCA_TRANSFER_CONSULT, OVERRIDE_SOFTKEY_SCA_TRANSFER_CONSULT
							4. Add new parameters SOFTKEY_SCA_DIALING, OVERRIDE_SOFTKEY_SCA_DIALING
							5. Add new parameters SOFTKEY_SCA_DIALTONE, OVERRIDE_SOFTKEY_SCA_DIALTONE
							6. Add new parameters SOFTKEY_DIALING, OVERRIDE_SOFTKEY_DIALING
							7. Add new parameters SOFTKEY_DIALTONE, OVERRIDE_SOFTKEY_DIALTONE
							8. Add new parameters SOFTKEY_TRANSFER_DIALING, OVERRIDE_SOFTKEY_TRANSFER_DIALING
							9. Add new parameters SOFTKEY_TRANSFER_OUTGOING, OVERRIDE_SOFTKEY_TRANSFER_OUTGOING
							10. Add new parameters SOFTKEY_TRANSFER_CONSULT, OVERRIDE_SOFTKEY_TRANSFER_CONSULT
							11. Add new parameters SOFTKEY_SCA_REMOTE_ACTIVE, OVERRIDE_SOFTKEY_SCA_REMOTE_ACTIVE
							12. Add new parameters SOFTKEY_SCA_REMOTE_HELD, OVERRIDE_SOFTKEY_SCA_REMOTE_HELD
							13. Add new parameters endptUSBHEADSETMODEL
							14. Add new parameters endptUSBHEADSETMANUFACTURER
							15. Add new parameters endptUSBHEADSETSN
							16. Add new parameters endptUSBHEADSETFW
							17. Add new parameter BLF_LIST_PREFERRED_START_LOCATION
							18. Add new parameter BLF_LIST_LINEKEY_LOCATION_FORCED
							19. Add new parameter AUTOMATIC_UPDATE_POLICY
							20. Add new parameter AUTOMATIC_UPDATE_DAYS
							21. Add new parameter AUTOMATIC_UPDATE_WINDOW
							22. Add new parameter AUTOMATIC_UPGRADE_INSTALL_DATE_TIME
							23. Add new parameter AUTOMATIC_UPDATE_REBOOT_PROMPT
							24. Add new parameter LOGSRVR_SECURE
							25. Add new parameter PUSH_MODE
							26. Add new parameter PUSHPORT_SECURE
							27. Add new parameter PHONE_KEY_LIST_ENHANCED
							28. Add new parameter NEXT_AUTOMATIC_UPDATE_INTERVAL
							29. Add new parameter LAST_UPDATE
                        Version 4.0.7.0
                            1. Modify parameter description endptSHAREDLINE<n>MAXCALLAPPEARANCES
							2. Modify parameter description endptSHAREDLINEMODE
							3. Add new parameter endptBEACONINDICATIONMODE
							4. Add new parameter endptVVMMODE
							5. Add new parameter endptVVMPASSCODEREQ
							6. Add new parameter endptVVMPLAYBACKNUM
							7. Add new parameter endptENABLEUSBHEADSET
							8. Add new parameter endptAGTGREETINGSTAT
							9. Add new parameter endptAGTGREETLOGOUTDEL
							10. Add new parameter endptAGENTGREETINGSDELAY
							11. Add new parameter endptENABLERANDOMRTPPORT
							12. Add new parameters endptSHAREDLINE<n>ENABLED (n=9,10)
							13. Add new parameters endptSHAREDLINE<n>MAXCALLAPPEARANCES (n=9,10)
							14. Add new parameters endptSHAREDLINE<n>SIPUSERID (n=9,10)
							15. Add new parameters endptSHAREDLINE<n>USERNAME (n=9,10)
							16. Add new parameters endptSHAREDLINE<n>EXTENSION (n=9,10)
							17. Add new parameters endptSHAREDLINE<n>BARGEINENABLED (n=9,10)
							18. Add new parameters endptSHAREDLINE<n>INCOMINGCALLINDICATIONDEFAULT (n=9,10)
							19. Add new parameters endptSHAREDLINE<n>INCOMINGCALLINDICATIONDELAYEDDEFAULT (n=9,10)
							20. Add new parameters endptSHAREDLINE<n>INCOMINGCALLINDICATION (n=9,10)
							21. Add new parameters endptSHAREDLINE<n>INCOMINGCALLINDICATIONDELAYED (n=9,10)
							22. Add new parameter endptVVMVOICEMAILKEY
							23. Add new parameter endptUSBPOWERLEVEL
							24. Add new parameter endptEXCHANGEAUTHMETHODDEFAULT
							25. Add new parameter endptEXCHANGEUSERACCOUNTDEFAULT
							26. Add new parameter endptEXCHANGEEMAILDOMAINUSER
							27. Add new parameter endptEXCHANGESERVERLISTUSER
							28. Add new parameter endptEXCHANGEAUTHMETHOD
                        Version 4.0.6.0
                            1. Modify parameter description APPLICATION_HEADER_APPEARANCE_CONTEXT
                            2. Modify parameter description ENABLE_OPUS
                            3. Add new parameter REST_URL
                            4. Add new parameter CALLFWD_CHAIN_ORDER
                            5. Modify parameter description IGNORE_BLF_LINE_KEY
                            6. Add new parameter SCA<n>_INCOMING_CALL_INDICATION_DEFAULT
                            7. Add new parameter SCA<n>_INCOMING_CALL_INDICATION_DELAYED_DEFAULT
                            8. Add new parameter SHARED_CALL_APPEARANCES_MODE
                            9. Add new parameter ENABLE_HOLD_REMINDER_DISPLAY
                            10. Modify parameter description BACKGROUND_IMAGE
                            11. Modify parameter description SCREENSAVER_IMAGE
                            12. Modify parameter description SCREENSAVER_IMAGE_DISPLAY
                            13. Add new parameter ENABLE_WMLPUSH_ALERTING
                            14. Add new parameter SOFTKEY_IDLE
                            15. Add new parameter SOFTKEY_ACTIVE
                            16. Add new parameter SOFTKEY_INCOMING_VISUAL
                            17. Add new parameter SOFTKEY_INCOMING
                            18. Add new parameter SOFTKEY_OUTGOING
                            19. Add new parameter SOFTKEY_ACTIVE_PAGETARGET
                            20. Add new parameter OVERRIDE_SOFTKEY_IDLE
                            21. Add new parameter OVERRIDE_SOFTKEY_ACTIVE
                            22. Add new parameter OVERRIDE_SOFTKEY_INCOMING_VISUAL
                            23. Add new parameter OVERRIDE_SOFTKEY_INCOMING
                            24. Add new parameter OVERRIDE_SOFTKEY_OUTGOING
                            25. Add new parameter OVERRIDE_SOFTKEY_ACTIVE_PAGETARGET
                            26. Add new parameter SOFTKEY_BLF_IDLE
                            27. Add new parameter SOFTKEY_BLF_ACTIVE
                            28. Add new parameter SOFTKEY_BLF_INCOMING_VISUAL
                            29. Add new parameter SOFTKEY_BLF_INCOMING
                            30. Add new parameter SOFTKEY_BLF_OUTGOING
                            31. Add new parameter OVERRIDE_SOFTKEY_BLF_IDLE
                            32. Add new parameter OVERRIDE_SOFTKEY_BLF_ACTIVE
                            33. Add new parameter OVERRIDE_SOFTKEY_BLF_INCOMING_VISUAL
                            34. Add new parameter OVERRIDE_SOFTKEY_BLF_INCOMING
                            35. Add new parameter OVERRIDE_SOFTKEY_BLF_OUTGOING
                            36. Add new parameter RTCP_XR
                            37. Add new parameter ENABLE_DIGIT_MAPPING
                            38. Add new parameter DIGIT_MAPPING
                            39. Add new parameter REJECT_PAGE_DURING_CALL
                            40. Add new parameter SCA<n>_INCOMING_CALL_INDICATION
                            41. Add new parameter SCA<n>_INCOMING_CALL_INDICATION_DELAYED
                        Version 4.0.5.0
                            1. Add new parameter APPLICATION_HEADER_APPEARANCE_CONTEXT
                            2. Add new parameter ENABLE_PARK_DYNAMIC_AND_PAGE
                            3. Add new parameter CALL_PARK_DYNAMIC_METHOD
                            4. Add new parameter CALL_PARK_DYNAMIC_FAC
                            5. Add new parameter CALL_PAGE_EXTENSION_FAC
                            6. Modify parameter description 3PCC_SERVER_MODE
                            7. Modify parameter description TIME_FORMAT 
                            8. Add new parameter ADMIN_TIME_FORMAT
                            9. Modify parameter description ENABLE_OPUS
                           10. Modify parameter description MAX_DNS_DISCOVERED_SIP_CONTROLLERS
                           11. Add new parameter SHORT_FORM_USER_ID
                           12. Add new parameter SHARED_LINE_MODE
                           13. Modify parameter description SCA_LINE_SEIZE_DURATION
                           14. Add new parameter SCA<n>_ENABLED <n> ranges from 4 to 8
                           16. Add new parameter SCA<n>_MAX_CALL_APPEARANCES <n> ranges from 4 to 8
                           17. Add new parameter SCA<n>_SIPUSERID <n> ranges from 4 to 8
                           18. Add new parameter SCA<n>_USERNAME <n> ranges from 4 to 8
                           19. Add new parameter SCA<n>_PASSWORD
                           20. Add new parameter SCA<n>_EXTENSION
                           21. Add new parameter SCA<n>_BARGE_IN_ENABLED
                           22. Modify parameter description PROVIDE_SHARED_LINE_CONFIG
                           23. Modify parameter description PRIMARY_LINE_TYPE
                           24. Modify parameter description PRIMARY_LINE_BARGE_IN_ENABLED
                           25. Modify parameter description DISPLAY_NAME
                           26. Add new parameter ENABLE_REDIAL_LIST
                           27. Add new parameter SHORTCUT_ACTION_CONTACT
                           28. Add new parameter SHORTCUT_ACTION_AUTODIAL
                           29. Add new parameter PHONE_LOCK_PIN
                           30. Add new parameter RTCP_PUBLISH_ADDRESS
                           31. Add new parameter CALL_PAGING_GROUPS
                           32. Add new parameter HOMEIDLETIME
                           33. Add new parameter CODEC_PRIORITY
                           34. Add new parameter EFFECT_OF_REDIAL_BUTTON
                           35. Add new parameter IGNORE_BLF_LINE_KEY 
                           36. Add new parameter ANSWERED_ELSEWHERE_POLICY
                           37. Add new parameter PRIMARY_LINE_EXTENSION
                           38. Add new parameter DIR_TO_LOCAL_MAPPING
                           39. Add new parameter DIR_LDAP_DESCRIPTION
                           40. Add new parameter CALL_PAGE_GROUP_FAC
                           41. Add new parameter PHONE_LOCK_IDLE_TIME_USER
                           42. Add new parameter PHONE_LOCK_PASSWORD_FAILED_ATTEMPTS
                           43. Add new parameter PHONE_LOCK_PASSWORD_LOCKED_TIME
                           44. Add new parameter IGNORE_LINE_KEY
                           45. Add new parameter SCROLLING_MODE
                           46. Add new parameter CALL_FORWARD_DELAY_USER
                           47. Modify parameter description SLMSTAT
                           48. Add new parameter KEYUSAGE_REQUIRED
                           49. Add new parameter LANGUAGES
                           50. Add new parameter SHOW_CALLFOR_ON_PRIMARY
                           51. Add new parameter REDIAL_LIST_MODE_DEFAULT
                           52. Add new parameter PHNDAC
                           53. Add new parameter ENABLE_SIPURI_HOST_VALIDATION
                           54. Add new parameter DOWNLOADABLE_DIRECTORY
                           55. Add new parameter DIALING_MODE_DEFAULT
                      	Version 4.0.4.0
                            1. Add new parameter BS_CC_DISP_CODES
                            2. Add new parameter BS_CC_SUPERVISORS
                            3. Add new parameter BS_CC_COT_ENABLED
                            4. Add new admin parameters for BLF alerting:
                                BLF_INCOMING_CALL_INDICATION_MODE
                                BLF_PARKED_CALL_INDICATION_MODE
                            5. Add new parameter SCEP_ENTITY_CLASS
                            6. Add new parameter ENABLE_GDPR_MODE
                            7. Add new parameter BS_CC_AUTOMATIC_STATE
                            8. Add new parameter ESCALATION_FAC
                            9. Add new parameter BLF_PICKUP_METHOD
                           10. Add new parameter ENABLE_RFC5922
                           11. Add new parameter AUTO_ANSWER_DURING_CALL
                           12. Add new parameter SOFTKEY_ACTIVE
                           13. Modified description for ENHDIALSTAT
                           14. Add new parameter DISPLAY_NAME
                           15. Add new parameter SYSLOG_LEVEL
                      	Version 4.0.3.0
                            1. Add new parameters for Secondary Display Background Image: 
								BACKGROUND_IMAGE_DISPLAY_SECONDARY
								BACKGROUND_IMAGE_SELECTABLE_SECONDARY
								BACKGROUND_IMAGE_SECONDARY
								BACKGROUND_IMAGE_AVAILABLE_SECONDARY //internal
                            2. Add new paramters for Secondary Display Screen Saver:
								SCREENSAVER_IMAGE_DISPLAY_SECONDARY
								SCREENSAVER_IMAGE_SELECTABLE_SECONDARY
								SCREENSAVER_IMAGE_SECONDARY
								SCREENSAVER_IMAGE_AVAILABLE_SECONDARY //internal
                            3. Add new paramter SECONDARY_DISPLAY_BRIGHTNESS 
                            4. Update description of parameters related to Netsapiens server
                            5. Add new parameter: PHONE_SCREEN_MODE
                            6. Add new parameter BW_HOTELING_MODE
                            7. Add new parameter RING_REMINDER_RINGTONE
                            8. Remove parameter BW_RING_REMINDER_RING_TYPE
                            9. Add new parameters for Broadsoft Call Center:
                                BS_CC_ENABLED
                                BS_CC_ACTIVE
                                BS_CC_UNAVAIL_CODES
                      	Version 4.0.2.0
                            1. Add new parameters for Multicast Paging feature
                            2. Add new parameters for TR78 and PNP
                            3. Add new parameters for NAT feature
                        Version 4.0.1.0
                            1. Add new parameters for NAT feature
                            2. Add new parameters for pre-configured phone keys feature
                            3. Add new parameter for Long term acoustic protection
                        Version 4.0.0.0
                            1. Add new parameters for Shared Line feature
                            2. Add new parameters for BLF feature
                            3. Add new parameters for BroadWorks features
                            4. Add new parameters for XSI to BroadWorks section
                            5. Add new parameter endptSIPDISCOVEREDPROXYLIST for registration redundancy
                            6. Add new parameter endptWLANMAXAUTHFAILRETRIES for Wi-Fi authentication failure retry
                            7. Add new parameter for IPV6 support
                            8. Updates for Shared Line feature
                        Version 2.0.0.0
                            1. Add new parameters specific for Wi-Fi: avayaSparkMIB 1, endptWIFI 1..23
                            2. Add new parameters to Wi-Fi group: endptWlanListSize, endptWlanListTable
                            3. Add new parameters: endptWLANL2PRIORITYFORAUDIO, endptWLANL2PRIORITYFORSIGNALING,
                                                   endptWLANDSCPFORAUDIO,endptWLANDSCPFORSIGNALING
                            4. Add endptENABLEOPUS.
                            5. Add endptVLANSEPMODE.
                            6. Add endptSHOWLASTEXTENSION.
                            7. Add new parameters to endptApps group: 
                                    endptGUESTLOGINSTAT, endptGUESTDURATION, 
                                    endptGUESTWARNING, endptGUESTLOGINACTIVE
                            8. Add new parameters specific for CCMS: ENABLE_IPOFFICE,
                                                    MEDIA_PRESERVATION, PRESERVED_CALL_DURATION
                            9. Add new parameters specific for Wi-Fi: 
                                    endptWIFIIGNOREDATEVALIDITYERROR, endptETHERNETCARRIERDETECTED, 
                                    endptWLANCOUNTRY, endptNETWORKCONFIGMANUAL, endptCHANGEOVERETHERNETTOWIFIACTIVE
                            10. Add new Wi-Fi parameter endptWLANENABLE80211D
                            11. Add new Wi-Fi parameter endptENABLENETWORKCONFIGBYUSER
                            12. Add new parameters specific for Wi-Fi to endptWlanListTable_entry:
                                    endptWlanFROMSETTINGSFILE, endptWlanSTORED, endptWlanAVAILABLE, endptWlanCONNECTED
                            13. Add endptIPV6DADXMITS, endptIPMODE, endptIPV6STAT, endptIPADDV6LL, endptIPADDV6, endptDHCPSTAT, endptSIGNALINGADDRMODE, endptMEDIAADDRMODE MIB items.
                            14. Add new Wi-Fi parameter endptWIFICHIPPRESENT
                            15. Add new parameters specific to Background and Screensaver: endptBACKGROUNDIMAGE,
                                    endptBACKGROUNDIMAGEDISPLAY, endptBACKGROUNDIMAGESELECTABLE, endptSCREENSAVERIMAGE, 
                                    endptSCREENSAVERIMAGEDISPLAY, endptSCREENSAVERIMAGESELECTABLE
                            16. Comment out sensitive Wi-Fi security parameters
                            17. Remove Wi-Fi parameter endptWIFIIGNOREDATEVALIDITYERROR
                            18. Add new parameters specific for Bluetooth
                                    endptBLUETOOTHSTAT, endptOPTBLUETOOTH, endptHANDSETTYPE
                            19. Add new parameters specific for Wi-Fi DHCP reuse
                                    endptREUSEWIFI, endptREUSEWIFIIPADDRESS, endptREUSEWIFISUBNETMASK,
                                    endptREUSEWIFIROUTERSLIST, endptREUSEWIFIROUTERINUSE
                            20. Add new customization parameter
                                    endptCUSTOMIZATIONMAP
                            21. Add new parameter endptSCREENSAVERCLOCKENABLE
                            22. Add new parameters endptSCREENSAVERIMAGEAVAILABLE, endptBACKGROUNDIMAGEAVAILABLE
                            23. Add new parameters endptHEADSETType, endptHEADSETGainDefault, endptDHCPSTD
                            24. Add new parameter endptWIFIDEBUGOPAQUESTRING,
                                    Enable non-sensitive secure Wi-Fi parameters 
                            25. Add endptAUDIOALERTMODE, endptHEADSETOPERATIONALMODE MIB items.
                            26. Add new parameters for DES Feature
                            27. Add new parameters for Web Server Feature
                        Version 1.1.0.0
                            1. Add EASG product certificate attributes.
                            2. Add endptEASGStatus, endptEASGSiteCerts, endptEASGSiteCertsWarningDays MIB items
                            3. Add endptMaxTrustCerts
                        Version 1.0.0.0 --initial release
                        "
                    ::= { ipEndpointMIBs 6 }

avaya                   OBJECT IDENTIFIER ::= { enterprises 6889 }
products                OBJECT IDENTIFIER ::= { avaya 1 }
avayaMibs               OBJECT IDENTIFIER ::= { avaya 2 }
avayaipEndpointProd     OBJECT IDENTIFIER ::= { products 69 }
ipEndpointMIBs          OBJECT IDENTIFIER ::= { avayaMibs 69 }      

avaya96x1SIPEndpoints   OBJECT IDENTIFIER ::= { avayaipEndpointProd 6 }
avaya9608SIP            OBJECT IDENTIFIER ::= { avaya96x1SIPEndpoints 1 }
avaya9611SIP            OBJECT IDENTIFIER ::= { avaya96x1SIPEndpoints 2 }
avaya9621SIP            OBJECT IDENTIFIER ::= { avaya96x1SIPEndpoints 3 }
avaya9641SIP            OBJECT IDENTIFIER ::= { avaya96x1SIPEndpoints 4 }
avaya9601SIP            OBJECT IDENTIFIER ::= { avaya96x1SIPEndpoints 5 }

endptID         OBJECT IDENTIFIER ::= { avayaSparkMIB 1 }
endptAGCHAND    OBJECT-TYPE
                    SYNTAX      INTEGER  
                    MAX-ACCESS  read-only
                    STATUS      current
                    DESCRIPTION "Handset AGC status. This variable
                        returns 1 if the endpoint's handset Automatic 
                        Gain Control capability is currently enabled,
                        else 0."
                    ::= { endptID 1 }
endptAGCHEAD    OBJECT-TYPE
                    SYNTAX      INTEGER  
                    MAX-ACCESS  read-only
                    STATUS      current
                    DESCRIPTION "Headset AGC status. This variable returns 1 
                        if the endpoint's headset Automatic Gain Control 
                        capability is currently enabled, else 0."
                    ::= { endptID 2 }
endptAGCSPKR    OBJECT-TYPE
                    SYNTAX      INTEGER  
                    MAX-ACCESS  read-only
                    STATUS      current
                    DESCRIPTION "Speakerphone AGC status. This variable returns 
                        1 if the endpoint's speakerphone Automatic Gain Control 
                        capability is currently enabled, else 0."
                    ::= { endptID 3 }
endptAPPINUSE   OBJECT-TYPE 
                    SYNTAX      DisplayString 
                    MAX-ACCESS  read-only
                    STATUS      current
                    DESCRIPTION "Application/Library software package.  This variable returns
                        the name of the Application/Library software package in the endpoint.
                        Phone with HWVERS up to 3 (as conveyed by endptHWVER) returns the filename of the Application/Library software package.
                        Phone with HWVERS 3 and up (as conveyed by endptHWVER) returns the firmware version of the active bank. 
                        "
                    ::= { endptID 4 }
endptAPPNAME    OBJECT-TYPE
                    SYNTAX      DisplayString
                    MAX-ACCESS  read-only
                    STATUS      current
                    DESCRIPTION "Application/Library software package. This variable returns 
                        a string specifying the system-specific Application/Library software package 
                        that should be used for telephone operation."
                    ::= { endptID 5 }
endptBAKLIGHTOFF  OBJECT-TYPE
                    SYNTAX      INTEGER
                    MAX-ACCESS  read-only
                    STATUS      current
                    DESCRIPTION "Backlight idle timer setting. This variable 
            returns the number of minutes of idle time, after which 
            the phone backlight is turned off. Range is 0-999, with  
            a default of 120.  Used in phones with backlit displays."                        
                    ::= { endptID 6 }
endptBACKUPAPP   OBJECT-TYPE
                    SYNTAX      DisplayString
                    MAX-ACCESS  read-only
                    STATUS      current
                    DESCRIPTION "Backup application package name. This variable returns  
                        a string specifying the name of the application package stored as a backup copy.
                        Phone with HWVERS up to 3 (as conveyed by endptHWVER) returns the filename of the Backup Application. 
                        Phone with HWVERS 3 and up (as conveyed by endptHWVER) returns the firmware version of the inactive bank. 
                        " 
                    ::= { endptID 7 }
endptBRIGHTNESS  OBJECT-TYPE
                    SYNTAX      INTEGER
                    MAX-ACCESS  read-only
                    STATUS      current
                    DESCRIPTION "Display Brightness setting. This variable  
            returns the value of the display brightness setting  
            in memory. Range is 0-5, with 4 the default."
                    ::= { endptID 8 }
endptCONFIGSRVR  OBJECT-TYPE
                    SYNTAX      DisplayString
                    MAX-ACCESS  read-only
                    STATUS      current
                    DESCRIPTION "Configuration Server. This variable returns  
            a string specifying the IP address or URL of the  
                        configuration server (e.g PPM) that should be used 
                        for endpoint configuration (only set if not identical 
                        to SIP Proxy server)."
                    ::= { endptID 9 }
endptCONFIGSRVRUSED  OBJECT-TYPE
                    SYNTAX      DisplayString
                    MAX-ACCESS  read-only
                    STATUS      current
                    DESCRIPTION "Configuration server IP address.  This 
            variable returns a 4-octet IP address for the  
            configuration server used during initialization 
                        (all zeros if no specific server used)."
                    ::= { endptID 10 }
endptCNAPORT    OBJECT-TYPE
                    SYNTAX      INTEGER
                    MAX-ACCESS  read-only
                    STATUS      obsolete
                    DESCRIPTION "Chatter server port. This variable returns the 
            Chatter server registration transport-layer port number 
            (from 0 to 65535; default is 8888)."
                    ::= { endptID 11 }
endptCNASRVR    OBJECT-TYPE
                    SYNTAX      DisplayString
                    MAX-ACCESS  read-only
                    STATUS      obsolete
                    DESCRIPTION "CNA server addresses. This variable returns zero 
            or more Chatter server addresses for network analysis, in 
            dotted decimal or DNS format."
                    ::= { endptID 12 }
endptCODECR     OBJECT-TYPE
                    SYNTAX      DisplayString
                    MAX-ACCESS  read-only
                    STATUS      current
                    DESCRIPTION "Receive codec(s). This variable returns the 
                        designation(s) of the Receive codec(s) currently 
                        in use."
                    ::= { endptID 13 }
endptCODECT     OBJECT-TYPE
                    SYNTAX      DisplayString
                    MAX-ACCESS  read-only
                    STATUS      current
                    DESCRIPTION "Transmit codec(s). This variable returns the 
                        designation(s) of the Transmit codec(s) currently 
                        in use."
                    ::= { endptID 14 }
endptCONTRAST    OBJECT-TYPE
                    SYNTAX      INTEGER
                    MAX-ACCESS  read-only
                    STATUS      current
                    DESCRIPTION "Display Contrast setting. This variable returns
            the value of the display contrast setting in memory.  
            Range is 0-15, with 8 the default."
                    ::= { endptID 15 }
endptCOUNTRY    OBJECT-TYPE
                    SYNTAX      DisplayString
                    MAX-ACCESS  read-only
                    STATUS      current
                    DESCRIPTION "Country specific network progress tone setting.   
                        This variable returns the designation of the country  
                        for which the user hears dial tone, ringing tone, busy 
                        tone, congestion tone, reorder tone and intercept tone."
                    ::= { endptID 16 }
endptDATEFORMAT  OBJECT-TYPE
                    SYNTAX      DisplayString
                    MAX-ACCESS  read-only
                    STATUS      current
                    DESCRIPTION "Date format string. This variable returns a 
                        string specifying the date separator and the position 
                        of day (%d), month (%m) and year (%y for 2-digit 
                        presentation, %Y for 4-digit presentation). 
                        Default is '%m/%d/%y' for date in mm/dd/yy format."
                    ::= { endptID 17 }
endptDHCPLEASEREBIND     OBJECT-TYPE
                    SYNTAX      Integer32
                    MAX-ACCESS  read-only
                    STATUS      current
                    DESCRIPTION "Rebind time of IPADD lease. This 
                        variable returns an unsigned integer specifying 
                        the length of time at which to rebind the IPADD 
            lease, in seconds as received by DHCP option 59."
                    ::= { endptID 18 }
endptDHCPLEASERENEW     OBJECT-TYPE
                    SYNTAX      Integer32
                    MAX-ACCESS  read-only
                    STATUS      current
                    DESCRIPTION "Renewal time of IPADD lease. This 
                        variable returns an unsigned integer specifying 
                        the length of time at which to renew the IPADD 
            lease, in seconds as received by DHCP option 58."
                    ::= { endptID 19 }
endptDHCPLEASETIME      OBJECT-TYPE
                    SYNTAX      Integer32
                    MAX-ACCESS  read-only
                    STATUS      current
                    DESCRIPTION "Duration of IPADD lease. This variable 
                        returns an unsigned integer specifying the length 
                        of time of the IPADD lease, in seconds as received 
                        by DHCP option 51."
                    ::= { endptID 20 }
endptDNSSRVR    OBJECT-TYPE
                    SYNTAX      DisplayString
                    MAX-ACCESS  read-only
                    STATUS      current
                    DESCRIPTION "List of DNS server addresses.  This variable 
            returns a sequence of IP addresses, in dotted-decimal 
            format and separated by commas, of DNS servers 
            available for use."
                    ::= { endptID 21 }
endptDOMAIN     OBJECT-TYPE
                    SYNTAX      DisplayString
                    MAX-ACCESS  read-only
                    STATUS      current
                    DESCRIPTION "Domain setting. This varialbe returns a string
                        to be appended to configuration parameters, when they 
                        are resolved into IP addresses."
                    ::= { endptID 22 }
endptDOT1X      OBJECT-TYPE
                    SYNTAX      INTEGER
                    MAX-ACCESS  read-only
                    STATUS      current
                    DESCRIPTION "802.1X mode. This variable returns 
            0 if the endpoint supports unicast Supplicant 
                        operation only, with PAE multicast pass-through 
                        without proxy Logoff, 1 if the same as 0 but with 
                        proxy Logoff, and 2 if both unicast or Multicast
                        Supplicant operation, without PAE multicast 
                        pass-through, is supported.  The default is 0." 
                    ::= { endptID 23 }
endptDSCPAUD    OBJECT-TYPE
                    SYNTAX      INTEGER  
                    MAX-ACCESS  read-only
                    STATUS      current
                    DESCRIPTION "DSCP for audio. This variable specifies the
                        Differentiated Services Code Point for audio 
                        currently in use (between 0 and 63 inclusive)."
                    ::= { endptID 24 }
endptDSCPBBE    OBJECT-TYPE
                    SYNTAX      INTEGER 
                    MAX-ACCESS  read-only
                    STATUS      current
                    DESCRIPTION "DSCP BBE priority value. This variable is   
            a placeholder for future use. It currently 
                        returns '-1'."
                    ::= { endptID 25 }
endptDSCPSIG    OBJECT-TYPE
                    SYNTAX      INTEGER  
                    MAX-ACCESS  read-only
                    STATUS      current
                    DESCRIPTION " DSCP for signaling. This variable specifies 
                        the Differentiated Services Code Point for signaling 
                        currently in use (between 0 and 63 inclusive)."
                    ::= { endptID 26 }
endptDSPVERSION  OBJECT-TYPE
                    SYNTAX      DisplayString
                    MAX-ACCESS  read-only
                    STATUS      current
                    DESCRIPTION "DSP Version.  This variable returns a string 
            of up to 10 characters, that identifies the version of 
            the DSP firmware in the endpoint."
                    ::= { endptID 27 }
endptFEIPADD    OBJECT-TYPE
                    SYNTAX      DisplayString
                    MAX-ACCESS  read-only
                    STATUS      current
                    DESCRIPTION "Audio endpoint address(es). This variable 
                        returns a string specifying the address(es) of the  
                        far-end audio endpoint(s) currently in use."
                    ::= { endptID 28 }
endptFEPORT     OBJECT-TYPE
                    SYNTAX      DisplayString
                    MAX-ACCESS  read-only
                    STATUS      current
                    DESCRIPTION "Audio endpoint port number(s). This variable 
                        returns the far-end endpoint's transport layer port  
                        number(s) for audio, currently in use."
                    ::= { endptID 29 }
endptFONT       OBJECT-TYPE
                    SYNTAX      DisplayString
                    MAX-ACCESS  read-only
                    STATUS      current
                    DESCRIPTION "Font file identifier. This variable returns a 
            text string with the name of the font file stored 
                        in the endpoint, if any."
                    ::= { endptID 30 }
endptGROUP      OBJECT-TYPE
                    SYNTAX      INTEGER  
                    MAX-ACCESS  read-only
                    STATUS      current
                    DESCRIPTION "Group identifier. This variable returns the 
                        integer corresponding to the current group identifier."
                    ::= { endptID 31 }
endptHTTPDIR    OBJECT-TYPE
                    SYNTAX      DisplayString
                    MAX-ACCESS  read-only
                    STATUS      current
                    DESCRIPTION "HTTP server directory.  This variable returns 
            the path used in formation of the URI for HTTP GET 
                        operations to access HTTP initialization server."
                    ::= { endptID 32 }
endptHTTPPORT    OBJECT-TYPE
                    SYNTAX      INTEGER
                    MAX-ACCESS  read-only
                    STATUS      current
                    DESCRIPTION "HTTP server port.  This variable returns the 
            port used for HTTP GET operations to access 
                        HTTP initialization server."
                    ::= { endptID 33 }
endptHTTPSRVR   OBJECT-TYPE
                    SYNTAX      DisplayString
                    MAX-ACCESS  read-only
                    STATUS      current
                    DESCRIPTION "HTTP server IP addresses.  This variable 
            returns a comma-separated list of HTTP server IP 
            addresses available  for use during initialization, 
                        in dotted-decimal or DNS format."
                    ::= { endptID 34 }
endptHTTPUSED   OBJECT-TYPE
                    SYNTAX      IpAddress
                    MAX-ACCESS  read-only
                    STATUS      current
                    DESCRIPTION "HTTP initialization server IP address. This 
            variable returns a 4-octet IP address for the HTTP  
            server used, if any, during initialization (all zeros  
            if no server successfully used during initialization)."
                    ::= { endptID 35 }
endptICMPDU     OBJECT-TYPE
                    SYNTAX      INTEGER
                    MAX-ACCESS  read-only
                    STATUS      current
                    DESCRIPTION "Current value for ICMP Destination message 
                        handling. This variable returns 0 if the endpoint does 
                        not transmit ICMP Destination Unreachable messages; 
                        1 if such messages are transmitted only in response to 
                        datagrams that designate closed UDP ports or if the 
                        designated transport protocol is not supported, and 
                        2 if such messages are sent only in response to 
                        datagrams that designate closed UDP or TCP ports or 
                        if the designated transport protocol is not supported.  
                        The default is 1." 
                    ::= { endptID 36 }
endptICMPRED    OBJECT-TYPE
                    SYNTAX      INTEGER
                    MAX-ACCESS  read-only
                    STATUS      current
                    DESCRIPTION "Current value for ICMP Redirect message 
                        handling. This variable returns 1 if received Redirect 
                        messages are handled as specified in RFC 1122, Sections
                        3.2.2.2 and 3.3.1.2, else 0. The default is 0."
                    ::= { endptID 37 }
endptIPADD      OBJECT-TYPE
                    SYNTAX      IpAddress
                    MAX-ACCESS  read-only
                    STATUS      current
                    DESCRIPTION "Endpoint IP address. This variable returns a 
            4-octet string specifying the endpoint's current 
                        IP address."
                    ::= { endptID 38 }
endptJMSEC      OBJECT-TYPE
                    SYNTAX      DisplayString
                    MAX-ACCESS  read-only
                    STATUS      current
                    DESCRIPTION "Jitter buffer size(s). This variable returns 
                        the number(s) of milliseconds of delay added to 
                        compensate for network jitter, from 0-300 milliseconds, 
                        for each active audio connection. The default is 10."                        
                    ::= { endptID 39 }
endptL2Q        OBJECT-TYPE
                    SYNTAX      INTEGER  
                    MAX-ACCESS  read-only
                    STATUS      current
                    DESCRIPTION "802.1Q framing flag. This variable returns 0 
            if the Layer 2 802.1Q framing parameter is set to 
            'auto', 1 if it is set to on/enabled, else 2 for
                        off/disabled."
                    ::= { endptID 40 }
endptL2QAUD     OBJECT-TYPE
                    SYNTAX      INTEGER  
                    MAX-ACCESS  read-only
                    STATUS      current
                    DESCRIPTION "Audio priority. This variable returns an 
                        integer between 0 and 7 inclusive specifying the 
                        current Layer 2 802.1Q audio priority value."
                    ::= { endptID 41 }
endptL2QSIG     OBJECT-TYPE
                    SYNTAX      INTEGER  
                    MAX-ACCESS  read-only
                    STATUS      current
                    DESCRIPTION "Signaling priority. This variable returns 
                        an integer between 0 and 7 inclusive specifying the 
                        current Layer 2 802.1Q signaling priority value."
                    ::= { endptID 42 }
endptL2QSTAT    OBJECT-TYPE
                    SYNTAX      INTEGER  
                    MAX-ACCESS  read-only
                    STATUS      current
                    DESCRIPTION "802.1Q tagging flag. This variable returns 0  
                        if the Layer 2 802.1Q tagging parameter is currently
                        OFF, else 1." 
                    ::= { endptID 43 }
endptL2QVLAN    OBJECT-TYPE
                    SYNTAX      INTEGER 
                    MAX-ACCESS  read-only
                    STATUS      current
                    DESCRIPTION "Administered Telephone VLAN Identifier. This  
                        variable returns an integer between 0 and 4094  
                        inclusive specifying the administered Layer 2  
                        802.1Q VLAN Identifier value."
                    ::= { endptID 44 }
endptL2QVLANINIT  OBJECT-TYPE
                    SYNTAX      INTEGER
                    MAX-ACCESS  read-only
                    STATUS      current
                    DESCRIPTION "Stored Telephone VLAN Identifier, This 
                        variable returns an integer between 0 and 4094   
                        inclusive specifying the stored Layer 2 802.1Q   
                        VLAN Identifier  value to accommodate requirement  
                        for VLAN Identifier survival."
                    ::= { endptID 45 }
endptL2QVLANINUSE OBJECT-TYPE
                    SYNTAX      INTEGER 
                    MAX-ACCESS  read-only
                    STATUS      current
                    DESCRIPTION "Telephone VLAN Identifier in use. This  
                        variable returns an integer between 0 and 4094   
                        inclusive specifying the current Layer 2  
                        802.1Q VLAN Identifier value."
                    ::= { endptID 46 }
endptLANGFILES  OBJECT-TYPE
                    SYNTAX      DisplayString
                    MAX-ACCESS  read-only
                    STATUS      current
                    DESCRIPTION "Language file list. This variable returns  
            a  string specifying the language files stored 
            in the endpoint,if any, separated by commas."
                    ::= { endptID 47 }
endptLANGINUSE  OBJECT-TYPE
                    SYNTAX      DisplayString
                    MAX-ACCESS  read-only
                    STATUS      current
                    DESCRIPTION "Language file in use. This variable returns
                        the name of the language currently used or the string 
                        'built-in', if the built-in language is used."
                    ::= { endptID 48 }
endptLOGSRVR    OBJECT-TYPE
                    SYNTAX      DisplayString
                    MAX-ACCESS  read-only
                    STATUS      current
                    DESCRIPTION "Event Log server address.  This variable 
            returns at most one IP address, in dotted-decimal 
            or DNS format, of the server to be used for event 
            logging.  This function is intended for Avaya use,
                        in debugging if necessary."
                    ::= { endptID 49 }
endptMACADDR    OBJECT-TYPE
                    SYNTAX      DisplayString
                    MAX-ACCESS  read-only
                    STATUS      current
                    DESCRIPTION "MAC address. This variable returns a 6-octet 
                        string specifying the endpoint's MAC address."
                    ::= { endptID 50 }
endptMEDIAENCRYPTION  OBJECT-TYPE
                    SYNTAX      DisplayString
                    MAX-ACCESS  read-only
                    STATUS      current
                    DESCRIPTION "Media encryption settings. This variable  
                        returns a string specifiying the cryptosuite and 
                        session parameter for media encryption.
                        1 = aescm128-hmac80 
                        2 = aescm128-hmac32
                        3 = aescm128-hmac80-unauth
                        4 = aescm128-hmac32-unauth
                        5 = aescm128-hmac80-unenc
                        6 = aescm128-hmac32-unenc
                        7 = aescm128-hmac80-unenc-unauth
                        8 = aescm128-hmac32-unenc-unauth
                        9 = none (default)
                        10 = aescm256-hmac80
                        11 = aescm256-hmac32
                        Options 10 and 11 are supported by 96x1 SIP R7.0.0 and later.           
                        Up to 2 or 3 options may be specified in a comma-separated list.
                        2 options are supported by Prior releases to 96x1 SIP 7.0.0
                        3 options are supported by 96x1 SIP R7.0.0 and later.
                        The options should match those specified in CM IP-codec-set form."
                    ::= { endptID 51 }
endptMODEL      OBJECT-TYPE
                    SYNTAX      DisplayString
                    MAX-ACCESS  read-only
                    STATUS      current
                    DESCRIPTION "Model identifier. This variable returns 
            a string of up to 8 ASCII characters."
                    ::= { endptID 52 }
endptMTUSIZE  OBJECT-TYPE
                    SYNTAX      INTEGER
                    MAX-ACCESS  read-only
                    STATUS      current
                    DESCRIPTION "Maximum Transmission Unit size. This  
                        variable returns the maximum number of octects 
                        in Ethernet frames. Possible values are 1496 and 1500, 
                        default is 1500. 1496 is possible to accommodate
                        older Ethernet switches that cannot support the longer 
                        maximum frame length of tagged frames."
                    ::= { endptID 53 }
endptNETMASK    OBJECT-TYPE
                    SYNTAX      IpAddress
                    MAX-ACCESS  read-only
                    STATUS      current
                    DESCRIPTION "Subnet mask. This variable returns a  
                        4-octet string specifying the subnet mask 
                        currently in use."
                    ::= { endptID 54 }
endptPERSONALRING  OBJECT-TYPE
                    SYNTAX      DisplayString
                    MAX-ACCESS  read-only
                    STATUS      current
                    DESCRIPTION "Ring pattern setting. This variable returns a 
                        string specifying the personal ringing pattern  
                        currently selected."
                    ::= { endptID 55 }
endptPHONECC     OBJECT-TYPE
                    SYNTAX      DisplayString
                    MAX-ACCESS  read-only
                    STATUS      current
                    DESCRIPTION "Phone comcode. This variable returns a string 
            of up to 9 numerical characters, specifying the comcode
                        of the endpoint itself." 
                    ::= { endptID 56 }
endptPHONESN    OBJECT-TYPE
                    SYNTAX      DisplayString
                    MAX-ACCESS  read-only
                    STATUS      current
                    DESCRIPTION "Housing serial number. This variable 
            returns a string of up to 18 ASCII characters, 
            specifying the serial number on the outside 
                        of the endpoint's housing."
                    ::= { endptID 57 }
endptPHY1DUPLEX OBJECT-TYPE
                    SYNTAX      INTEGER 
                    MAX-ACCESS  read-only
                    STATUS      current
                    DESCRIPTION "Ethernet line interface duplex setting. This  
            variable returns 1 if the interface is half-duplex and 
                        2 if the interface is full duplex."
                    ::= { endptID 58 }
endptPHY1OPERATIONALMODE  OBJECT-TYPE
                    SYNTAX      INTEGER 
                    MAX-ACCESS  read-only
                    STATUS      current
                    DESCRIPTION "Ethernet interface speed. This variable 
            returns a string specifying the endpoint's Ethernet
            interface speed in Mbps: '1000', '100' or '10'."
                    ::= { endptID 59 }
endptPHY1STAT   OBJECT-TYPE
                    SYNTAX      INTEGER  
                    MAX-ACCESS  read-only
                    STATUS      current
                    DESCRIPTION "Ethernet line interface administration.  
            This variable returns 1, if the Ethernet line 
            interface is currently for auto-negotiation, 2 for 
            10Mbps half-duplex, 3 for 10Mbps full-duplex, 4 for 
            100Mbps half-duplex, 5 for 100Mbps full-duplex, 
            and 6 for 1000Mbps full-duplex (if supported 
                        by hardware)."
                    ::= { endptID 60 }
endptPHY2DUPLEX OBJECT-TYPE
                    SYNTAX      INTEGER 
                    MAX-ACCESS  read-only
                    STATUS      current
                    DESCRIPTION "Secondary Ethernet interface duplex setting.  
            This variable returns 0 if no link is established, 
                        1 if the interface is half-duplex, and 2 if 
                        the interface is full duplex."
                    ::= { endptID 61 }
endptPHY2PRIO   OBJECT-TYPE
                    SYNTAX      INTEGER  
                    MAX-ACCESS  read-only
                    STATUS      current
                    DESCRIPTION "Secondary Ethernet interface Layer 2 priority. 
            This variable returns 0 through 7, and is used with   
                        endptVLANSEP. The default is 0."
                    ::= { endptID 62 }
endptPHY2OPERATIONALMODE  OBJECT-TYPE
                    SYNTAX      INTEGER 
                    MAX-ACCESS  read-only
                    STATUS      current
                    DESCRIPTION "Secondary Ethernet speed. This variable 
            returns a string specifying the endpoint's Ethernet
            interface speed in Mbps: '1000', '100' or '10' or '0'."
                    ::= { endptID 63 }
endptPHY2STAT   OBJECT-TYPE
                    SYNTAX      INTEGER  
                    MAX-ACCESS  read-only
                    STATUS      current
                    DESCRIPTION "Secondary Ethernet interface administration.  
            This variable returns 0 if the endpoint's Secondary 
                        Ethernet interface is currently NOT enabled, 1 if the 
                        Secondary Ethernet interface is currently for    
            auto-negotiation, 2 for 10Mbps half-duplex, 3 for  
            10Mbps full-duplex, 4 for 100Mbps half-duplex, 5 for  
            100Mbps full-duplex, and 6 for 1000Mbps full-duplex 
                        (if supported by hardware)."
                    ::= { endptID 64 }
endptPHY2VLAN   OBJECT-TYPE
                    SYNTAX      INTEGER  
                    MAX-ACCESS  read-only
                    STATUS      current
                    DESCRIPTION "Secondary Ethernet interface VLAN ID. This 
            variable returns an integer between 0 and 4094  
                        inclusive specifying the current Layer 2 802.1Q  
                        VLAN Identifier value for tagged frames received  
                        on the secondary Ethernet interface while VLAN 
                        separation is enabled."
                    ::= { endptID 65 }
endptPORTAUD    OBJECT-TYPE
                    SYNTAX      DisplayString
                    MAX-ACCESS  read-only
                    STATUS      current
                    DESCRIPTION "Transport-layer audio port(s). This variable 
                        returns the endpoint's transport layer port number(s) 
                        for audio connection(s), currently in use."
                    ::= { endptID 66 }
endptPROCPSWD   OBJECT-TYPE
                    SYNTAX      DisplayString
                    MAX-ACCESS  read-only
                    STATUS      obsolete
                    DESCRIPTION "Local Procedure Password. This variable returns
                        0 if the Local Procedure Password is null, else 1."
                    ::= { endptID 67 }
endptPROCSTAT   OBJECT-TYPE
                    SYNTAX      INTEGER  
                    MAX-ACCESS  read-only
                    STATUS      current
                    DESCRIPTION "Local Procedure flag. This variable returns 
                        0 if Local Procedures are currently allowed for this 
                        endpoint, else 1."
                    ::= { endptID 68 }
endptPWBCC      OBJECT-TYPE
                    SYNTAX      DisplayString
                    MAX-ACCESS  read-only
                    STATUS      obsolete
                    DESCRIPTION "PWB comcode. This variable returns  
                        a string of up to 9 numerical characters, 
                        specifying the comcode or version number of 
                        the printed wiring board of the endpoint."
                    ::= { endptID 69 }
endptPWBSN      OBJECT-TYPE
                    SYNTAX      DisplayString
                    MAX-ACCESS  read-only
                    STATUS      obsolete
                    DESCRIPTION "PWB serial number. This variable 
            returns a string of up to 18 ASCII characters, 
            specifying the serial number on the endpoint's 
            printed wiring board, or N/A if the board has 
                        no serial number."
                    ::= { endptID 70 }
endptROUTER     OBJECT-TYPE
                    SYNTAX      DisplayString
                    MAX-ACCESS  read-only
                    STATUS      current
                    DESCRIPTION "List of router addresses.  This variable 
            returns a sequence of IP addresses, in  
            dotted-decimal format and separated by commas, 
                        of routers available for use."
                    ::= { endptID 71 }
endptROUTERINUSE   OBJECT-TYPE
                    SYNTAX      IpAddress
                    MAX-ACCESS  read-only
                    STATUS      current
                    DESCRIPTION "Router address.  This variable returns  
                        a 4-octet string specifying the IP address of 
                        the router currently in use."
                    ::= { endptID 72 }
endptRSVPCONT   OBJECT-TYPE
                    SYNTAX      INTEGER 
                    MAX-ACCESS  read-only
                    STATUS      current
                    DESCRIPTION "RSVP Control flag. This variable is   
            a placeholder for future use. It currently 
                        returns '-1'."
                    ::= { endptID 73 }
endptRSVPRFRSH  OBJECT-TYPE
                    SYNTAX      INTEGER 
                    MAX-ACCESS  read-only
                    STATUS      current
                    DESCRIPTION "RSVP Refresh rate. This variable is   
            a placeholder for future use. It currently 
                        returns '-1'."
                    ::= { endptID 74 }
endptRSVPRTRY   OBJECT-TYPE
                    SYNTAX      INTEGER 
                    MAX-ACCESS  read-only
                    STATUS      current
                    DESCRIPTION "RSVP Failed Retry flag. This variable 
            is a placeholder for future use. It currently 
                        returns '-1'."
                    ::= { endptID 75 }
endptRSVPPROF   OBJECT-TYPE
                    SYNTAX      INTEGER 
                    MAX-ACCESS  read-only
                    STATUS      current
                    DESCRIPTION "RSVP profile flag. This variable is   
            a placeholder for future use. It currently 
                        returns '-1'."
                    ::= { endptID 76 }
endptRTCPCONT   OBJECT-TYPE
                    SYNTAX      INTEGER 
                    MAX-ACCESS  read-only
                    STATUS      current
                    DESCRIPTION "RTCP Control flag. This variable returns
                        0 if the RTCP control status is off/disabled, else 1."
                    ::= { endptID 77 }
endptRTCPFLOW   OBJECT-TYPE
                    SYNTAX      INTEGER 
                    MAX-ACCESS  read-only
                    STATUS      current
                    DESCRIPTION "RTCP Flowrate. This variable returns
                        an integer between 5 and 30 inclusive specifying the
                        RTCP flowrate in seconds."
                    ::= { endptID 78 }
endptRTCPMON    OBJECT-TYPE
                    SYNTAX      IpAddress
                    MAX-ACCESS  read-only
                    STATUS      current
                    DESCRIPTION "RTCP Monitor address.  This variable returns a 
                        4-octet string specifying the IP address of the RTCP
                        monitor currently in use."
                    ::= { endptID 79 }
endptRTCPMONPORT  OBJECT-TYPE
                    SYNTAX      INTEGER
                    MAX-ACCESS  read-only
                    STATUS      current
                    DESCRIPTION "RTCP Monitor port. This variable returns the 
            RTCP monitor transport-layer destination port number 
            (from 0 to 65535; default is 5005)."
                    ::= { endptID 80 }
endptSENDDTMFTYPE  OBJECT-TYPE
                    SYNTAX      INTEGER
                    MAX-ACCESS  read-only
                    STATUS      current
                    DESCRIPTION "DTMF mode. This variable returns 1 if 
                        the endpoint sends DTMF in-band tones, and 2 for 
                        negotiation and transmission of DTMF according to 
                        RFC 2833."
                    ::= { endptID 81 }
endptSIG        OBJECT-TYPE
                    SYNTAX      INTEGER  
                    MAX-ACCESS  read-only
                    STATUS      current
                    DESCRIPTION "Signaling protocol download flag. This  
                        variable returns the integer corresponding to the 
                        current signaling protocol."
                    ::= { endptID 82 }
endptSKININUSE   OBJECT-TYPE
                    SYNTAX      DisplayString
                    MAX-ACCESS  read-only
                    STATUS      current
                    DESCRIPTION "Current skin definition. This variable returns
                        a label specifying the skin definition currently used.
                        If built-in default skin defintion is used, it is empty.
                        Otherwise it contains the skin label as received with  
                        the corresponding skin file downloaded at 
                        endpoint initialization."
                    ::= { endptID 83 }
endptSNMPADD    OBJECT-TYPE
                    SYNTAX      DisplayString
                    MAX-ACCESS  read-only
                    STATUS      current
                    DESCRIPTION "SNMP source addresses. This variable returns 
            one or more allowable source IP addresses for SNMP 
                        queries, in dotted decimal or DNS format."
                    ::= { endptID 84 }
endptSSON    OBJECT-TYPE
                    SYNTAX      INTEGER
                    MAX-ACCESS  read-only
                    STATUS      current
                    DESCRIPTION "Site-specific option number. This variable 
                        returns an integer between 128 and 254 inclusive,
                        specifying the SSON stored.  The default is 242."
                    ::= { endptID 85 }
endptSPEAKERSTAT  OBJECT-TYPE
                    SYNTAX      INTEGER
                    MAX-ACCESS  read-only
                    STATUS      current
                    DESCRIPTION "Speakerphone mode. This varialbe returns 
                        the current speakerphone mode: 0 if speakerphone 
                        capability is disabled or not existing, 1 if 
                        one-way speakerphone operation (monitor) is possible, 
                        and 2 if two-way speakerphone operation is possible."
                    ::= { endptID 86 }
endptSYSLOGENABLED   OBJECT-TYPE
                    SYNTAX      INTEGER
                    MAX-ACCESS  read-only
                    STATUS      current
                    DESCRIPTION "Remote logging status. This variable returns 
                        0 if transmission of log messages to the log server 
                        is disabled, else 1."
                    ::= { endptID 87 }
endptTCPKEEPALIVESTAT  OBJECT-TYPE
                    SYNTAX      INTEGER
                    MAX-ACCESS  read-only
                    STATUS      current
                    DESCRIPTION "TCP keep alive status. This variable returns 
                        0 if TCP keep alive is NOT performed, else 1."
                    ::= { endptID 88 }
endptTIMEFORMAT  OBJECT-TYPE
                    SYNTAX      INTEGER
                    MAX-ACCESS  read-only
                    STATUS      current
                    DESCRIPTION "Time Format setting. 
                    Non-Aura & Non-IPO CCMS TIMEFORMAT
                    0 - default (default value use ADMINTIMEFORMAT)
                    1 - am/pm
                    2 - 24h (this is the new value)

                    Aura TIMEFORMAT
                    0 - am/pm (default)
                    1 = 24h"
                    ::= { endptID 89 }
endptTLSDIR     OBJECT-TYPE
                    SYNTAX      DisplayString
                    MAX-ACCESS  read-only
                    STATUS      current
                    DESCRIPTION "TLS server Directory.  This variable returns 
            the path used in formation of the URI for HTTPS GET 
                        operations to access TLS initialization server."
                    ::= { endptID 90 }
endptTLSPORT    OBJECT-TYPE
                    SYNTAX      INTEGER
                    MAX-ACCESS  read-only
                    STATUS      current
                    DESCRIPTION "TLS server Port.  This variable returns the 
            port used for HTTPS GET operations to access 
                        TLS initialization server."
                    ::= { endptID 91 }
endptTLSSRVR    OBJECT-TYPE
                    SYNTAX      DisplayString
                    MAX-ACCESS  read-only
                    STATUS      current
                    DESCRIPTION "TLS server addresses. This variable returns  
            zero or more Transport Layer Security server addresses 
                        for use during initialization, in dotted decimal or 
                        DNS format."
                    ::= { endptID 92 }
endptTLSUSED    OBJECT-TYPE
                    SYNTAX      IpAddress
                    MAX-ACCESS  read-only
                    STATUS      current
                    DESCRIPTION "TLS server address used. This variable  
            returns the TLS server address from TLSSRVR used,  
            if any, during  initialization, or all zeroes if 
                        no TLS server was used."
                    ::= { endptID 93 }
endptTMSEC      OBJECT-TYPE
                    SYNTAX      DisplayString
                    MAX-ACCESS  read-only
                    STATUS      current
                    DESCRIPTION "Transmit audio packetization delay(s). This 
                        variable returns the number(s) of milliseconds of  
                        delay added by packetization and coding for audio 
                        transmission for each active audio connection."
                    ::= { endptID 94 }
endptUSEDHCP    OBJECT-TYPE
                    SYNTAX      INTEGER
                    MAX-ACCESS  read-only
                    STATUS      current
                    DESCRIPTION "DHCP mode. This variable returns 0 if IP 
                        address is a static configuration, or 1 
                        if a dynamic IP address is received via DHCP."
                    ::= { endptID 95 }
endptVLANSEP    OBJECT-TYPE
                    SYNTAX      INTEGER  
                    MAX-ACCESS  read-only
                    STATUS      current
                    DESCRIPTION "VLAN separation value. This variable returns 0
             if frames received on the secondary Ethernet interface 
                         are unchanged before forwarding; else 1, which is 
                         the default."
                    ::= { endptID 96 }
endptVLANTEST    OBJECT-TYPE
                    SYNTAX      INTEGER
                    MAX-ACCESS  read-only
                    STATUS      current
                    DESCRIPTION "VLAN pause parameter. This variable returns 
                        the number of seconds stored for the endpoint to 
                        wait for a DHCPOFFER message when using a non-zero   
                        VLAN ID. Valid values are integers from 0 to 999 
                        inclusive."
                    ::= { endptID 97 }
endptTRUSTCERTS  OBJECT-TYPE
                    SYNTAX      DisplayString
                    MAX-ACCESS  read-only
                    STATUS      current
                    DESCRIPTION "Trusted Certificate URLs. This variable returns
                        the URLs of certificate files that are considered as  
                        trusted certificates and requested to download into 
                        the endpoint at boot-time."
                    ::= { endptID 98 }
endptMYCERTURL    OBJECT-TYPE
                    SYNTAX      DisplayString
                    MAX-ACCESS  read-only
                    STATUS      current
                    DESCRIPTION "SCEP server URL. This variable returns a  
                        string specifying the URL of the SCEP (Simple 
                        Certificate Enrollment Protocol) server used for 
                        certificate enrollment."
                    ::= { endptID 99 }
endptMYCERTCN   OBJECT-TYPE
                    SYNTAX      DisplayString
                    MAX-ACCESS  read-only
                    STATUS      current
                    DESCRIPTION "Common Name for Subject in SCEP request. 
                        This variable returns '$SERIALNO' if the endpoint's 
                        serial number is included in the SCEP request, 
                        or'$MACADDR' if its MAC address is used instead."
                    ::= { endptID 100 }
endptMYCERTDN   OBJECT-TYPE
                    SYNTAX      DisplayString
                    MAX-ACCESS  read-only
                    STATUS      current
                    DESCRIPTION "Subject definition for SCEP request. 
                         This variable returns the part in a SCEP request, 
                         which is common for requests from different 
                         Avaya SIP endpoints."
                    ::= { endptID 101 }
endptMYCERTKEYLEN  OBJECT-TYPE
                    SYNTAX      INTEGER
                    MAX-ACCESS  read-only
                    STATUS      current
                    DESCRIPTION "Private key length. This varialbe returns 
                        the length of the private key in bits to be created 
                        in the endpoint for certificate enrollment. 
                        The default is 1024 bits."
                    ::= { endptID 102 }
endptMYCERTRENEW  OBJECT-TYPE
                    SYNTAX      INTEGER
                    MAX-ACCESS  read-only
                    STATUS      current
                    DESCRIPTION "Certificate renewal threshold. 
                        This variable returns an integer between 1 and 99 
                        inclusive specifying the moment the endpoint starts 
                        to contact the SCEP server for certificate renewal. 
                        It is specified by a percentage to be applied to 
                        the device certificate's validity Object."
                    ::= { endptID 103 }
endptMYCERTWAIT  OBJECT-TYPE
                    SYNTAX      INTEGER
                    MAX-ACCESS  read-only
                    STATUS      current
                    DESCRIPTION "Certificate wait flag. This variable returns 
                        0 if certificate enrollment is done periodically in 
                        the background, and 1 if the endpoint waits to continue 
                        with startup operation until a response from SCEP 
                        server is received."
                    ::= { endptID 104 }
endptHTTPPROXY  OBJECT-TYPE
                    SYNTAX      DisplayString
                    MAX-ACCESS  read-only
                    STATUS      current
                    DESCRIPTION "HTTP Proxy for SCEP. This variable returns 
            a string specifying a HTTP proxy IP address, in 
                        dotted-decimal or DNS format, optionally follwed by a 
                        colon and port number. If the variable is NOT null,
                        this transport address is used to set up HTTP 
                        connection for SCEP. "
                    ::= { endptID 105 }
endptHTTPEXCEPTIONDOMAINS  OBJECT-TYPE
                    SYNTAX      DisplayString
                    MAX-ACCESS  read-only
                    STATUS      current
                    DESCRIPTION "HTTP exception domains for SCEP. This 
                        variable returns a comma-separated list of zero or 
                        more domain names. A HTTP connection for SCEP
                        is NOT set up via HTTPPROXY, if the rightmost part 
                        of MYCERTURL matches one of the values of the 
                        listed domains."
                    ::= { endptID 106 }
endptAUTHONLY  OBJECT-TYPE
                    SYNTAX      INTEGER
                    MAX-ACCESS  read-only
                    STATUS      current
                    DESCRIPTION "Authentication flag for setting file download. 
                        This variable returns 0 if setting files are allowed to 
                        be received via HTTP and HTTPs, and 1, if they are only 
                        allowed to be received via HTTPS."
                    ::= { endptID 107 }
endptLOGCATEGORY  OBJECT-TYPE
                    SYNTAX      DisplayString
                    MAX-ACCESS  read-only
                    STATUS      current
                    DESCRIPTION "Logging category list. This variable returns 
                        zero or more keywords representing endpoint functions 
                        to be included in lower level logging (i.e. traces 
                        for level 'warning' or lower) or the string 'All' 
                        meaning lower level logging is performed for each 
                        endpoint function. Default is an empty string, which  
                        precludes any lower level logging." 
                    ::= { endptID 108 }
endptTRUSTLIST    OBJECT-TYPE
                    SYNTAX      DisplayString
                    MAX-ACCESS  read-only
                    STATUS      current
                    DESCRIPTION "Trusted Certificate list. This variable  
                        returns the names of the trusted certificate files  
                        that are successfully downloaded into the endpoint."
                    ::= { endptID 109 }
endptMYCERTCAID   OBJECT-TYPE
                    SYNTAX      DisplayString
                    MAX-ACCESS  read-only
                    STATUS      current
                    DESCRIPTION "Certificate Authority (CA) Identifier. 
                        This variable returns the CA Identitifier string
                        included in GET certificate requests."
                    ::= { endptID 110 }
endptPHNEMERGNUM  OBJECT-TYPE
                    SYNTAX      DisplayString
                    MAX-ACCESS  read-only
                    STATUS      current
                    DESCRIPTION "Emergency number. This variable returns
                        a string specifying the emergency number to be  
                        outpulsed when the user presses Emergency softkey."
                    ::= { endptID 111 }
endptDOT1XSTAT    OBJECT-TYPE
                    SYNTAX      INTEGER
                    MAX-ACCESS  read-only
                    STATUS      current
                    DESCRIPTION "802.1X status. This variable returns 
            0 if Supplicant operation is disabled, 1 if
                        supplicant operation is enabled, but endpoint 
                        responds only to recieved unicast EAPOL messages,  
                        and 2 if supplicant operation is enabled, and
                        endpoint responds to received unicast and multicast
                        EAPOL messages. The default is 1."
                    ::= { endptID 112 }
endptDOT1XEAPS    OBJECT-TYPE
                    SYNTAX      DisplayString
                    MAX-ACCESS  read-only
                    STATUS      current
                    DESCRIPTION "802.1X EAP methods. This variable 
                        returns a list of EAP authentication method(s)
                        the endpoint supports. The default is 'MD5,TLS'."
                    ::= { endptID 113 }
endptLLDPSTAT     OBJECT-TYPE
                    SYNTAX      INTEGER
                    MAX-ACCESS  read-only
                    STATUS      current
                    DESCRIPTION "LLDP status. This variable returns 
            0 if LLDP operation is disabled, 1 if
                        LLDP operation is enabled, and 2 (auto) if 
                        the endpoint supports LLDP, but the transmission
                        of LLDP frames does not begin until or unless
                        an LLDP frame is received. The default is 2."
                    ::= { endptID 114 }
endptPOECONSSUPPORT  OBJECT-TYPE
                    SYNTAX      INTEGER
                    MAX-ACCESS  read-only
                    STATUS      current
                    DESCRIPTION "Power over Ethernet conservation support.
                        This variable returns 0 if power over Ethernet 
                        conservation support is disabled, and 1 if it is 
                        enabled. The default is 'ON'."
                    ::= { endptID 115 }
endptPOECONSMODE  OBJECT-TYPE
                    SYNTAX      INTEGER
                    MAX-ACCESS  read-only
                    STATUS      current
                    DESCRIPTION "Power over Ethernet conservation mode.
                        This variable returns the endpoint's current power
                        over Ethernet conservation mode. It returns 0 for
                        'OFF' and 1 for 'ON'."
                    ::= { endptID 116 }
endptNVTRUSTCERTS  OBJECT-TYPE
                    SYNTAX      DisplayString
                    MAX-ACCESS  read-only
                    STATUS      current
                    DESCRIPTION "The last value of TRUSTCERTS explicitly
                        set in the configuration file."
                    ::= { endptID 117 }
endptCONFIGSERVERSECUREMODE  OBJECT-TYPE
                    SYNTAX      INTEGER
                    MAX-ACCESS  read-only
                    STATUS      current
                    DESCRIPTION "Communication mode to the configuration server.
                        This variable returns 0 if the endpoint is using HTTP to 
                        communicate with the configuration server, 1 if using HTTPS, 
                        and 2 if using HTTPS if the SIP transport type is TLS and 
                        HTTP if the SIP transport is not TLS."
                    ::= { endptID 118 }
endptSUPPORTGIGABIT  OBJECT-TYPE
                    SYNTAX      INTEGER
                    MAX-ACCESS  read-only
                    STATUS      current
                    DESCRIPTION "An indication that the phone supports Gigabit 
                        Ethernet. This variable returns a 0 if the endpoint does not 
                        support Gigabit Ethernet and 1 if it does support 
                        Gigabit Ethernet."
                    ::= { endptID 119 }
endptTLSSRVRID      OBJECT-TYPE
                    SYNTAX      INTEGER
                    MAX-ACCESS  read-only
                    STATUS      current
                    DESCRIPTION "Indicates if TLS server identification is required.
                        This variable returns a 0 if no certificate match is necessary
                        and 1 if a certificate match is required."
                    ::= { endptID 120 }
endptVLANLIST    OBJECT-TYPE SYNTAX      DisplayString
                    MAX-ACCESS  read-only
                    STATUS      current
                    DESCRIPTION "VLAN ID list. This variable returns a list of zero or more VLAN IDs." 
                    ::= { endptID 121 }
endptENABLEG711A      OBJECT-TYPE
                    SYNTAX      INTEGER
                    MAX-ACCESS  read-only
                    STATUS      current
                    DESCRIPTION "Indicates whether the G711A codec is enabled or disabled.
                        This variable returns a 0 if the codec is disabled
                        and 1 if the codec is enabled (default)."
                    ::= { endptID 122 }
endptENABLEG711U      OBJECT-TYPE
                    SYNTAX      INTEGER
                    MAX-ACCESS  read-only
                    STATUS      current
                    DESCRIPTION "Indicates whether the G711U codec is enabled or disabled.
                        This variable returns a 0 if the codec is disabled
                        and 1 if the codec is enabled (default)."
                    ::= { endptID 123 }
endptENABLEG729      OBJECT-TYPE
                    SYNTAX      INTEGER
                    MAX-ACCESS  read-only
                    STATUS      current
                    DESCRIPTION "Indicates the status of the G729 codec.
                        This variable returns a 0 if the codec is disabled. It returns a 1 when the phone 
                        advertises a preference for G.729(A) enabled, without Annex B support in an outbound INVITE request, 
                        and accepts either G729A or G729A with annex B support [G.729AB] when received in a 200OK response 
                        or an incoming INVITE request. It returns a 2 when the phone advertises a preference for 
                        G.729(A) enabled, with Annex B support [G.729AB] in an outbound INVITE request, 
                        and accepts either G729A or G729AB when received in a 200OK response or an incoming INVITE request."
                    ::= { endptID 124 }
endptENABLEG722      OBJECT-TYPE
                    SYNTAX      INTEGER
                    MAX-ACCESS  read-only
                    STATUS      current
                    DESCRIPTION "Indicates whether the G722 codec is enabled or disabled.
                        This variable returns a 0 if the codec is disabled (default)
                        and 1 if the codec is enabled."
                    ::= { endptID 125 }
endptENABLEG726      OBJECT-TYPE
                    SYNTAX      INTEGER
                    MAX-ACCESS  read-only
                    STATUS      current
                    DESCRIPTION "Indicates whether the G726 codec is enabled or disabled.
                        This variable returns a 0 if the codec is disabled
                        and 1 if the codec is enabled (default)."
                    ::= { endptID 126 }
endptSYSTEMLANGUAGE  OBJECT-TYPE
                    SYNTAX      DisplayString
                    MAX-ACCESS  read-only
                    STATUS      current
                    DESCRIPTION "System Default Language. This variable returns
                        the name of the file that contains the language strings currently used."
                    ::= { endptID 127 }
endptLANG0STAT      OBJECT-TYPE
                    SYNTAX      INTEGER
                    MAX-ACCESS  read-only
                    STATUS      current
                    DESCRIPTION "Indicates whether or not the built-in English is offered to the user 
                        as selectable item in the language selection menu.
                        This variable returns a 0 if the built-in English is not offered
                        and 1 if it is selectable item in the languauge selection menu."
                    ::= { endptID 128 }
endptRFSINUSE    OBJECT-TYPE
                    SYNTAX      DisplayString
                    MAX-ACCESS  read-only
                    STATUS      current
                    DESCRIPTION "In-use Kernel/Root File System Software Package name.  This variable 
                        returns the name of the Kernel/Root File
                System package in the endpoint from which the active Kernel/Root File System 
                        files were installed.
                        This MIB item is not applicable for phones with HWVERS 3 and up as conveyed by endptHWVER.                       
                        "
                    ::= { endptID 129 }
endptRFSNAME    OBJECT-TYPE
                    SYNTAX      DisplayString
                    MAX-ACCESS  read-only
                    STATUS      current
                    DESCRIPTION "The Kernel/Root File System Software Package.  This variable returns the name of the file 
                        that contains the Kernel/Root File System package for the endpoint.
                        This MIB item is not applicable for phones with HWVERS 3 and up as conveyed by endptHWVER
                        "
                    ::= { endptID 130 }
endpBOOT1INUSE OBJECT-TYPE
                    SYNTAX      DisplayString 
                    MAX-ACCESS  read-only
                    STATUS      current
                    DESCRIPTION "Boot1 filename. This variable returns the name of the boot1 file stored in the telephone.
                    This MIB item is not applicable for phones with HWVERS 3 and up as conveyed by endptHWVER."
                    ::= { endptID 131 }
endpBOOT2INUSE OBJECT-TYPE
                    SYNTAX      DisplayString 
                    MAX-ACCESS  read-only
                    STATUS      current
                    DESCRIPTION "Boot2 filename. This variable returns the name of the boot2 file stored in the telephone.
                    This MIB item is not applicable for phones with HWVERS 3 and up as conveyed by endptHWVER."
                    ::= { endptID 132 }
endptSLMSTAT     OBJECT-TYPE
                    SYNTAX      INTEGER
                    MAX-ACCESS  read-only
                    STATUS      current
                    DESCRIPTION "Indicates whether the SLA monitor agent is enabled or disabled.
                        This variable returns a 
                        0 if the monitor is disabled (default)
                        1 if the monitor is enabled
                        2 if the monitor is enabled in remote worker mode"
                    ::= { endptID 133 }
endptRINGTONESKB OBJECT-TYPE
                    SYNTAX      INTEGER
                    MAX-ACCESS  read-only
                    STATUS      current
                    DESCRIPTION "Indicates ringtone file storage size.
                        This variable returns the kilobytes occupied by
                        files downloaded via the RINGTONE parameter."
                    ::= { endptID 134 }
endptTUNINGFILE  OBJECT-TYPE
                    SYNTAX      INTEGER
                    MAX-ACCESS  read-only
                    STATUS      current
                    DESCRIPTION "Audio tuning flag.  This variable
                        returns a 1 if the audio software is currently
                        using information from a downloaded audio tuning 
                        file, else 0."
                    ::= { endptID 135 }
endptWARNINGFILE OBJECT-TYPE
                    SYNTAX      INTEGER
                    MAX-ACCESS  read-only
                    STATUS      current
                    DESCRIPTION "Call recording warning file flag.  This 
                        variable returns a 1 if call recording is 
                        configured to use a downloaded warning file, else 
                        0."
                    ::= { endptID 136 }   
                    
endptPHY2AUTOMDIXENABLED OBJECT-TYPE
                    SYNTAX      INTEGER
                    MAX-ACCESS  read-only
                    STATUS      current
                    DESCRIPTION "Secondary Ethernet interface Auto MDIX status.  
                    This variable returns 0 if the endpoint's Secondary 
                    Ethernet interface Auto MDIX is currently disabled, 
                    else 1 (default)."
                    ::= { endptID 137 }

endptHEADSETPROFILE OBJECT-TYPE
                    SYNTAX      INTEGER
                    MAX-ACCESS  read-only
                    STATUS      current
                    DESCRIPTION "This variable returns the value of HEADSET_PROFILE
                    which specifies the headset audio profile number selected by the user or 
                    0 if the user has not selected a profile. 0 is the default value.
                    "
                    ::= { endptID 138 }            
                                        
endptHWVER          OBJECT-TYPE
                    SYNTAX      INTEGER
                    MAX-ACCESS  read-only
                    STATUS      current
                    DESCRIPTION "This variable returns the value of HWVERS
                    which specifies the hardware version of the endpoint. 
                    "
                    ::= { endptID 139 }   

endptLNQ            OBJECT-TYPE
                    SYNTAX      INTEGER  
                    MAX-ACCESS  read-only
                    STATUS      current
                    DESCRIPTION "This MIB item returns the Local Network Quality level. 
                    0 if no local network quality is available,
                    else 6 if packet loss is < 1% and round-trip network delay is < 400 milliseconds and jitter compensation delay is < 80 milliseconds,
                    else 5 if packet loss is < 2% and round-trip network delay is < 425 milliseconds and jitter compensation delay is < 100 milliseconds, 
                    else 4 if packet loss is < 3% and round-trip network delay is < 450 milliseconds and jitter compensation delay is < 120 milliseconds, 
                    else 3 if packet loss is < 4% and round-trip network delay is < 475 milliseconds and jitter compensation delay is < 160 milliseconds,
                    else 2 if packet loss is < 5% and round-trip network delay is < 500 milliseconds and jitter compensation delay is < 200 milliseconds, 
                    else 1."
                    ::= { endptID 140 }

endptFIPSTEST       OBJECT-TYPE
                    SYNTAX      INTEGER  
                    MAX-ACCESS  read-only
                    STATUS      current
                    DESCRIPTION "result of the FIPS startup self-test.
                                0 = failed, 
                                1 = success
                                Default value: 0.
                                "
                    ::= { endptID 141 }

endptFIPSENABLED    OBJECT-TYPE
                    SYNTAX      INTEGER  
                    MAX-ACCESS  read-only
                    STATUS      current
                    DESCRIPTION "Specifies whether only FIPS-approved cryptographic algorithms will be supported.
                                Value  Operation:
                                0 - No restriction on using non FIPS-approved cryptographic algorithms (default)
                                1 - Use only FIPS-approved cryptographic algorithms
                                "
                    ::= { endptID 142 }

endptPKCS12URL      OBJECT-TYPE
                    SYNTAX      DisplayString  
                    MAX-ACCESS  read-only
                    STATUS      current
                    DESCRIPTION "URL for PKCS12."
                    ::= { endptID 143 }             

endptOCSPENABLED    OBJECT-TYPE
                    SYNTAX      INTEGER  
                    MAX-ACCESS  read-only
                    STATUS      current
                    DESCRIPTION "0 if OCSP disabled.
                    1 if OCSP enabled."
                    ::= { endptID 144 }

endptOCSPURI        OBJECT-TYPE
                    SYNTAX      DisplayString  
                    MAX-ACCESS  read-only
                    STATUS      current
                    DESCRIPTION "URL for OCSP."
                    ::= { endptID 145 }

endptOCSPURIPREF    OBJECT-TYPE
                    SYNTAX      INTEGER  
                    MAX-ACCESS  read-only
                    STATUS      current
                    DESCRIPTION "1 - Prefer OCSP_URI first, then AIA.
                    2 - Prefer AIA first then OCSP_URI."
                    ::= { endptID 146 }

endptOCSPACCEPTUNK  OBJECT-TYPE
                    SYNTAX      INTEGER  
                    MAX-ACCESS  read-only
                    STATUS      current
                    DESCRIPTION "0 - Treat certificate as revoked if status unknown.
                    1 - Accept certificate if status unknown."
                    ::= { endptID 147 }

endptOCSPNONCE      OBJECT-TYPE
                    SYNTAX      INTEGER  
                    MAX-ACCESS  read-only
                    STATUS      current
                    DESCRIPTION "0 - Nonce is not added to OCSP request.
                    1 - Nonce is added to OCSP request."
                    ::= { endptID 148 }

endptTLSVERSION     OBJECT-TYPE
                    SYNTAX      INTEGER  
                    MAX-ACCESS  read-only
                    STATUS      current
                    DESCRIPTION "0 - TLS 1.0 and up are permitted.
                    1 - TLS 1.2 and up are permitted."
                    ::= { endptID 149 }

endptENCRYPTSRTCP   OBJECT-TYPE
                    SYNTAX      INTEGER  
                    MAX-ACCESS  read-only
                    STATUS      current
                    DESCRIPTION "Use EncryptSrtcp.
                    0 - no.
                    1 - yes."
                    ::= { endptID 150 }

endptFQDNIPMAP      OBJECT-TYPE
                    SYNTAX      DisplayString  
                    MAX-ACCESS  read-only
                    STATUS      current
                    DESCRIPTION "FQDN ip map"
                    ::= { endptID 151 }

endptSERVERCERTRECHECKHOURS     OBJECT-TYPE
                                SYNTAX      INTEGER  
                                MAX-ACCESS  read-only
                                STATUS      current
                                DESCRIPTION "how often certs will be checked. 
                                Default value: 24.
                                Max value: 32767"
                                ::= { endptID 152 }

endptCERTWARNINGDAYS    OBJECT-TYPE
                        SYNTAX      INTEGER  
                        MAX-ACCESS  read-only
                        STATUS      current
                        DESCRIPTION "How long cert warnings will be provided
                        Default value: 60.
                        Max value: 99"
                        ::= { endptID 153 }

endptFIPSOPERATIONALMODE    OBJECT-TYPE
                            SYNTAX      INTEGER  
                            MAX-ACCESS  read-only
                            STATUS      current
                            DESCRIPTION " Allows an administrator to verify that the phone is actually running in a FIPS compliant mode.
                                        0 - FIPS mode is disabled, (Default)
                                        1 - FIPS mode is enabled but not compliant, 
                                        2 - FIPS mode is enabled and compliant.
                                        "
                            ::= { endptID 154 }

endptFIPSEXCEPTIONREASON    OBJECT-TYPE
                            SYNTAX      DisplayString  
                            MAX-ACCESS  read-only
                            STATUS      current
                            DESCRIPTION "Contains a comma-separated list of features/processes which 
                                        are active and cause the phone to not be operating in a FIPS compliant mode.
                                        Only applicable if FIPS_OPERATIONAL_MODE=1
                                        "
                            ::= { endptID 155 } 

endptBRURI          OBJECT-TYPE
                    SYNTAX      DisplayString
                    MAX-ACCESS  read-only
                    STATUS      current
                    DESCRIPTION "Report server URI. This variable returns 
                    a string specifying the URI used to upload a report file."                        
                    ::= { endptID 156 }

endptTrustCertTable  OBJECT-TYPE
          SYNTAX SEQUENCE OF EndptIdentityCertAttributes
          MAX-ACCESS    not-accessible
          STATUS        current
          DESCRIPTION   "Table of trust certificate's attributes"
          ::= { endptID 157 }
                    
endptIdentityCertAttributes OBJECT-TYPE
          SYNTAX EndptIdentityCertAttributes
          MAX-ACCESS    not-accessible
          STATUS        current
          DESCRIPTION   "Certificate's attribute struct"
          INDEX     { endptIdentityCertAttributeIndex }
          ::= { endptTrustCertTable 1 }
            
EndptIdentityCertAttributes     ::= 
            SEQUENCE  {
                endptIdentityCertAttributeIndex INTEGER,
                endptIdentityCertIssuerName DisplayString,
                endptIdentityCertSubjectName DisplayString,
                endptIdentityCertNotBefore DisplayString,
                endptIdentityCertNotAfter DisplayString,
                endptIdentityCertSN DisplayString,
                endptIdentityCertKeyUsageExtensions DisplayString,
                endptIdentityCertExtendedKeyUsage DisplayString,
                endptIdentityCertAltname DisplayString,
                endptIdentityCertFingerprint DisplayString,
                endptIdentityCertBasicContraints  DisplayString
                }   
                    
endptIdentityCertAttributeIndex     OBJECT-TYPE
        SYNTAX  INTEGER
            MAX-ACCESS  not-accessible
            STATUS  current
            DESCRIPTION
                    "cert attribute index."
            ::= { endptIdentityCertAttributes 1 }   
                    
endptIdentityCertIssuerName  OBJECT-TYPE
          SYNTAX        DisplayString (SIZE(0..255))
          MAX-ACCESS    read-only
          STATUS        current
          DESCRIPTION   "Issuer cert attribute"
          ::= { endptIdentityCertAttributes 2 }     
                    
endptIdentityCertSubjectName  OBJECT-TYPE
          SYNTAX        DisplayString (SIZE(0..255))
          MAX-ACCESS    read-only
          STATUS        current
          DESCRIPTION   "Subject cert attribute"
          ::= { endptIdentityCertAttributes 3 } 
          
endptIdentityCertNotBefore  OBJECT-TYPE
          SYNTAX        DisplayString (SIZE(0..255))
          MAX-ACCESS    read-only
          STATUS        current
          DESCRIPTION   "NotBefore cert attribute"
          ::= { endptIdentityCertAttributes 4 }     
          
endptIdentityCertNotAfter  OBJECT-TYPE
          SYNTAX        DisplayString (SIZE(0..255))
          MAX-ACCESS    read-only
          STATUS        current
          DESCRIPTION   "NotAfter cert attribute"
          ::= { endptIdentityCertAttributes 5 } 

endptIdentityCertSN     OBJECT-TYPE
          SYNTAX        DisplayString (SIZE(0..255))
          MAX-ACCESS    read-only
          STATUS  current
          DESCRIPTION  "SerialNumber cert attribute (Displayed by HEX string)"
          ::= { endptIdentityCertAttributes 6 } 

endptIdentityCertKeyUsageExtensions     OBJECT-TYPE
          SYNTAX        DisplayString (SIZE(0..255))
          MAX-ACCESS    read-only
          STATUS  current
          DESCRIPTION  "KeyUsage cert attribute"
          ::= { endptIdentityCertAttributes 7 } 

endptIdentityCertExtendedKeyUsage     OBJECT-TYPE
          SYNTAX        DisplayString (SIZE(0..255))
          MAX-ACCESS    read-only
          STATUS  current
          DESCRIPTION  "ExKeyUsage cert attribute"
          ::= { endptIdentityCertAttributes 8 } 
      
endptIdentityCertAltname  OBJECT-TYPE
          SYNTAX        DisplayString (SIZE(0..255))
          MAX-ACCESS    read-only
          STATUS        current
          DESCRIPTION   "Altname of certificate"
          ::= { endptIdentityCertAttributes 9 } 
          
endptIdentityCertFingerprint  OBJECT-TYPE
          SYNTAX        DisplayString (SIZE(0..255))
          MAX-ACCESS    read-only
          STATUS        current
          DESCRIPTION   "Sha1Hash of cert (Displayed by HEX string)"
          ::= { endptIdentityCertAttributes 10 }          
                    
endptIdentityCertBasicContraints     OBJECT-TYPE
          SYNTAX        DisplayString (SIZE(0..255))
          MAX-ACCESS    read-only
          STATUS  current
          DESCRIPTION  "BasicConstrains cert attribute"
          ::= { endptIdentityCertAttributes 11 }
                    
endptOCSPTrustCertTable  OBJECT-TYPE
          SYNTAX SEQUENCE OF EndptIdentityOCSPCertAttributes
          MAX-ACCESS    not-accessible
          STATUS        current
          DESCRIPTION   "Table of OCSP trust certificate's attributes"
          ::= { endptID 158 }
           
endptIdentityOCSPCertAttributes OBJECT-TYPE
          SYNTAX EndptIdentityOCSPCertAttributes
          MAX-ACCESS    not-accessible
          STATUS        current
          DESCRIPTION   "OCSP certificate's attribute struct"
          INDEX     { endptIdentityOCSPCertAttributeIndex }
          ::= { endptOCSPTrustCertTable 1 }
            
EndptIdentityOCSPCertAttributes     ::= 
            SEQUENCE  {
                endptIdentityOCSPCertAttributeIndex INTEGER,
                endptIdentityOCSPCertIssuerName DisplayString,
                endptIdentityOCSPCertSubjectName DisplayString,
                endptIdentityOCSPCertNotBefore DisplayString,
                endptIdentityOCSPCertNotAfter DisplayString,
                endptIdentityOCSPCertSN DisplayString,
                endptIdentityOCSPCertKeyUsageExtensions DisplayString,
                endptIdentityOCSPCertExtendedKeyUsage DisplayString,
                endptIdentityOCSPCertAltname DisplayString,
                endptIdentityOCSPCertFingerprint DisplayString,
                endptIdentityOCSPCertBasicContraints  DisplayString
                }   
                    
endptIdentityOCSPCertAttributeIndex     OBJECT-TYPE
        SYNTAX  INTEGER
            MAX-ACCESS  not-accessible
            STATUS  current
            DESCRIPTION
                    "OCSP cert attribute index."
            ::= { endptIdentityOCSPCertAttributes 1 }   
                    
endptIdentityOCSPCertIssuerName  OBJECT-TYPE
          SYNTAX        DisplayString (SIZE(0..255))
          MAX-ACCESS    read-only
          STATUS        current
          DESCRIPTION   "Issuer OCSP cert attribute"
          ::= { endptIdentityOCSPCertAttributes 2 }     
                    
endptIdentityOCSPCertSubjectName  OBJECT-TYPE
          SYNTAX        DisplayString (SIZE(0..255))
          MAX-ACCESS    read-only
          STATUS        current
          DESCRIPTION   "Subject OCSP cert attribute"
          ::= { endptIdentityOCSPCertAttributes 3 } 
          
endptIdentityOCSPCertNotBefore  OBJECT-TYPE
          SYNTAX        DisplayString (SIZE(0..255))
          MAX-ACCESS    read-only
          STATUS        current
          DESCRIPTION   "NotBefore OCSP cert attribute"
          ::= { endptIdentityOCSPCertAttributes 4 }     
          
endptIdentityOCSPCertNotAfter  OBJECT-TYPE
          SYNTAX        DisplayString (SIZE(0..255))
          MAX-ACCESS    read-only
          STATUS        current
          DESCRIPTION   "NotAfter OCSP cert attribute"
          ::= { endptIdentityOCSPCertAttributes 5 } 

endptIdentityOCSPCertSN     OBJECT-TYPE
          SYNTAX        DisplayString (SIZE(0..255))
          MAX-ACCESS    read-only
          STATUS  current
          DESCRIPTION  "SerialNumber OCSP cert attribute (Displayed by HEX string)"
          ::= { endptIdentityOCSPCertAttributes 6 } 

endptIdentityOCSPCertKeyUsageExtensions     OBJECT-TYPE
          SYNTAX        DisplayString (SIZE(0..255))
          MAX-ACCESS    read-only
          STATUS  current
          DESCRIPTION  "KeyUsage OCSP cert attribute"
          ::= { endptIdentityOCSPCertAttributes 7 } 

endptIdentityOCSPCertExtendedKeyUsage     OBJECT-TYPE
          SYNTAX        DisplayString (SIZE(0..255))
          MAX-ACCESS    read-only
          STATUS  current
          DESCRIPTION  "ExKeyUsage OCSP cert attribute"
          ::= { endptIdentityOCSPCertAttributes 8 } 
      
endptIdentityOCSPCertAltname  OBJECT-TYPE
          SYNTAX        DisplayString (SIZE(0..255))
          MAX-ACCESS    read-only
          STATUS        current
          DESCRIPTION   "Altname OCSP of certificate"
          ::= { endptIdentityOCSPCertAttributes 9 } 
          
endptIdentityOCSPCertFingerprint  OBJECT-TYPE
          SYNTAX        DisplayString (SIZE(0..255))
          MAX-ACCESS    read-only
          STATUS        current
          DESCRIPTION   "Sha1Hash of OCSP cert (Displayed by HEX string)"
          ::= { endptIdentityOCSPCertAttributes 10 }          
                    
endptIdentityOCSPCertBasicContraints     OBJECT-TYPE
          SYNTAX        DisplayString (SIZE(0..255))
          MAX-ACCESS    read-only
          STATUS  current
          DESCRIPTION  "BasicConstrains OCSP cert attribute."
          ::= { endptIdentityOCSPCertAttributes 11 }
endptOCSPHASHALGORITHM          OBJECT-TYPE
            SYNTAX      INTEGER
            MAX-ACCESS  read-only
            STATUS      current
            DESCRIPTION "Report the ocsp hash alorithm method."                        
            ::= { endptID 159 } 

endptAdminLoginAttemptAllowed          OBJECT-TYPE
            SYNTAX      INTEGER
            MAX-ACCESS  read-only
            STATUS      current
            DESCRIPTION "Report the Admin Login attempt Allowed."                        
            ::= { endptID 160 } 
endptAdminLoginLockedTime          OBJECT-TYPE
            SYNTAX      INTEGER
            MAX-ACCESS  read-only
            STATUS      current
            DESCRIPTION "Report the Admin Locked time."                        
            ::= { endptID 161 } 
endptDisplaySSLVersion          OBJECT-TYPE
            SYNTAX      INTEGER
            MAX-ACCESS  read-only
            STATUS      current
            DESCRIPTION "Report the display SSL Version."                        
            ::= { endptID 162 }     

endptOcspUseCache          OBJECT-TYPE
            SYNTAX      INTEGER
            MAX-ACCESS  read-only
            STATUS      current
            DESCRIPTION "Report the ocsp use Cache"           
            ::= { endptID 163 } 
endptOcspCacheExpiry          OBJECT-TYPE
            SYNTAX      INTEGER
            MAX-ACCESS  read-only
            STATUS      current
            DESCRIPTION "Report pcsp cathe expriry"        
            ::= { endptID 164 } 
endptDeleteMyCert          OBJECT-TYPE
            SYNTAX      INTEGER
            MAX-ACCESS  read-only
            STATUS      current
            DESCRIPTION "Report whether is it delete my certificate"
            ::= { endptID 165 } 
                        
endptMycertTypeInuse          OBJECT-TYPE
            SYNTAX      INTEGER
            MAX-ACCESS  read-only
            STATUS      current
            DESCRIPTION "Report my certificate type in use
                         0 -- Certificate is installed via SCEP
                         1 -- Certificate is installed via PKCS12
                         2 -- Certificate is installed via PKCS12 in FIPS mode"                     
            ::= { endptID 166 }     
                    
endptPkcs12PasswdRetry          OBJECT-TYPE
            SYNTAX      INTEGER
            MAX-ACCESS  read-only
            STATUS      current
            DESCRIPTION "Report the PKCS password retry."                        
            ::= { endptID 167 } 
endptOpenSSLVersion          OBJECT-TYPE
            SYNTAX      DisplayString
            MAX-ACCESS  read-only
            STATUS      current
            DESCRIPTION "Report the Open SSL version."                        
            ::= { endptID 168 }     
endptOpenSSHVersion          OBJECT-TYPE
            SYNTAX      DisplayString
            MAX-ACCESS  read-only
            STATUS      current
            DESCRIPTION "Report the Open SSH version."                        
            ::= { endptID 169 } 
endptEnergyEfficientEthernet          OBJECT-TYPE
            SYNTAX      INTEGER
            MAX-ACCESS  read-only
            STATUS      current
            DESCRIPTION "Report Energy-Efficient Ethernet status.
            0: EEE is disabled on both PHY1 and PHY2.
            1: EEE is enabled on both PHY1 and PHY2."                        
            ::= { endptID 170 } 
endptMyCertTable  OBJECT-TYPE
          SYNTAX SEQUENCE OF EndptMyCertAttributes
          MAX-ACCESS    not-accessible
          STATUS        current
          DESCRIPTION   "Table of identity certificate's attributes"
          ::= { endptID 171 }

endptMyCertAttributes OBJECT-TYPE
          SYNTAX EndptMyCertAttributes
          MAX-ACCESS    not-accessible
          STATUS        current
          DESCRIPTION   "Identity certificate's attribute struct"
          INDEX     { endptMyCertAttributeIndex }
          ::= { endptMyCertTable 1 }
            
EndptMyCertAttributes     ::= 
            SEQUENCE  {
                endptMyCertAttributeIndex INTEGER,
                endptMyCertIssuerName DisplayString,
                endptMyCertSubjectName DisplayString,
                endptMyCertNotBefore DisplayString,
                endptMyCertNotAfter DisplayString,
                endptMyCertSN DisplayString,
                endptMyCertKeyUsageExtensions DisplayString,
                endptMyCertExtendedKeyUsage DisplayString,
                endptMyCertAltname DisplayString,
                endptMyCertFingerprint DisplayString,
                endptMyCertBasicContraints  DisplayString
                }   
                    
endptMyCertAttributeIndex     OBJECT-TYPE
        SYNTAX  INTEGER
            MAX-ACCESS  not-accessible
            STATUS  current
            DESCRIPTION
                    "Identity cert attribute index."
            ::= { endptMyCertAttributes 1 } 
                    
endptMyCertIssuerName  OBJECT-TYPE
          SYNTAX        DisplayString (SIZE(0..255))
          MAX-ACCESS    read-only
          STATUS        current
          DESCRIPTION   "Issuer identity cert attribute"
          ::= { endptMyCertAttributes 2 }   
                    
endptMyCertSubjectName  OBJECT-TYPE
          SYNTAX        DisplayString (SIZE(0..255))
          MAX-ACCESS    read-only
          STATUS        current
          DESCRIPTION   "Subject identity cert attribute"
          ::= { endptMyCertAttributes 3 } 
          
endptMyCertNotBefore  OBJECT-TYPE
          SYNTAX        DisplayString (SIZE(0..255))
          MAX-ACCESS    read-only
          STATUS        current
          DESCRIPTION   "NotBefore identity cert attribute"
          ::= { endptMyCertAttributes 4 }   
          
endptMyCertNotAfter  OBJECT-TYPE
          SYNTAX        DisplayString (SIZE(0..255))
          MAX-ACCESS    read-only
          STATUS        current
          DESCRIPTION   "NotAfter identity cert attribute"
          ::= { endptMyCertAttributes 5 } 

endptMyCertSN     OBJECT-TYPE
          SYNTAX        DisplayString (SIZE(0..255))
          MAX-ACCESS    read-only
          STATUS  current
          DESCRIPTION  "SerialNumber identity cert attribute (Displayed by HEX string)"
          ::= { endptMyCertAttributes 6 }   

endptMyCertKeyUsageExtensions     OBJECT-TYPE
          SYNTAX        DisplayString (SIZE(0..255))
          MAX-ACCESS    read-only
          STATUS  current
          DESCRIPTION  "KeyUsage identity cert attribute"
          ::= { endptMyCertAttributes 7 }   

endptMyCertExtendedKeyUsage     OBJECT-TYPE
          SYNTAX        DisplayString (SIZE(0..255))
          MAX-ACCESS    read-only
          STATUS  current
          DESCRIPTION  "ExKeyUsage identity cert attribute"
          ::= { endptMyCertAttributes 8 }   
      
endptMyCertAltname  OBJECT-TYPE
          SYNTAX        DisplayString (SIZE(0..255))
          MAX-ACCESS    read-only
          STATUS        current
          DESCRIPTION   "Altname identity of certificate"
          ::= { endptMyCertAttributes 9 } 
          
endptMyCertFingerprint  OBJECT-TYPE
          SYNTAX        DisplayString (SIZE(0..255))
          MAX-ACCESS    read-only
          STATUS        current
          DESCRIPTION   "Sha1Hash of identity cert (Displayed by HEX string)"
          ::= { endptMyCertAttributes 10 }        
                    
endptMyCertBasicContraints     OBJECT-TYPE
          SYNTAX        DisplayString (SIZE(0..255))
          MAX-ACCESS    read-only
          STATUS  current
          DESCRIPTION  "BasicConstrains identity cert attribute."
          ::= { endptMyCertAttributes 11 } 
          
endptEASGProdCertTable  OBJECT-TYPE
          SYNTAX SEQUENCE OF EndptEASGProdCertAttributes
          MAX-ACCESS    not-accessible
          STATUS        current
          DESCRIPTION   "Table of EASG product certificate's attributes"
          ::= { endptID 172 }               
                
endptEASGProdCertAttributes OBJECT-TYPE
          SYNTAX EndptEASGProdCertAttributes
          MAX-ACCESS    not-accessible
          STATUS        current
          DESCRIPTION   "EASG product certificate's attribute struct"
          INDEX     { endptEASGProdCertAttributeIndex }
          ::= { endptEASGProdCertTable 1 }
            
EndptEASGProdCertAttributes     ::= 
            SEQUENCE  {
                endptEASGProdCertAttributeIndex INTEGER,
                endptEASGProdCertIssuerName DisplayString,
                endptEASGProdCertSubjectName DisplayString,
                endptEASGProdCertNotBefore DisplayString,
                endptEASGProdCertNotAfter DisplayString,
                endptEASGProdCertSN DisplayString,
                endptEASGProdCertKeyUsageExtensions DisplayString,
                endptEASGProdCertExtendedKeyUsage DisplayString,
                endptEASGProdCertAltname DisplayString,
                endptEASGProdCertFingerprint DisplayString,
                endptEASGProdCertBasicContraints  DisplayString
                }   
                    
endptEASGProdCertAttributeIndex     OBJECT-TYPE
        SYNTAX  INTEGER
            MAX-ACCESS  not-accessible
            STATUS  current
            DESCRIPTION
                    "EASG product cert attribute index."
            ::= { endptEASGProdCertAttributes 1 }   
                    
endptEASGProdCertIssuerName  OBJECT-TYPE
          SYNTAX        DisplayString (SIZE(0..255))
          MAX-ACCESS    read-only
          STATUS        current
          DESCRIPTION   "Issuer EASG product cert attribute"
          ::= { endptEASGProdCertAttributes 2 }     
                    
endptEASGProdCertSubjectName  OBJECT-TYPE
          SYNTAX        DisplayString (SIZE(0..255))
          MAX-ACCESS    read-only
          STATUS        current
          DESCRIPTION   "Subject EASG product cert attribute"
          ::= { endptEASGProdCertAttributes 3 } 
          
endptEASGProdCertNotBefore  OBJECT-TYPE
          SYNTAX        DisplayString (SIZE(0..255))
          MAX-ACCESS    read-only
          STATUS        current
          DESCRIPTION   "NotBefore EASG product cert attribute"
          ::= { endptEASGProdCertAttributes 4 }     
          
endptEASGProdCertNotAfter  OBJECT-TYPE
          SYNTAX        DisplayString (SIZE(0..255))
          MAX-ACCESS    read-only
          STATUS        current
          DESCRIPTION   "NotAfter EASG product cert attribute"
          ::= { endptEASGProdCertAttributes 5 } 

endptEASGProdCertSN     OBJECT-TYPE
          SYNTAX        DisplayString (SIZE(0..255))
          MAX-ACCESS    read-only
          STATUS  current
          DESCRIPTION  "SerialNumber EASG product cert attribute (Displayed by HEX string)"
          ::= { endptEASGProdCertAttributes 6 } 

endptEASGProdCertKeyUsageExtensions     OBJECT-TYPE
          SYNTAX        DisplayString (SIZE(0..255))
          MAX-ACCESS    read-only
          STATUS  current
          DESCRIPTION  "KeyUsage EASG product cert attribute"
          ::= { endptEASGProdCertAttributes 7 } 

endptEASGProdCertExtendedKeyUsage     OBJECT-TYPE
          SYNTAX        DisplayString (SIZE(0..255))
          MAX-ACCESS    read-only
          STATUS  current
          DESCRIPTION  "ExKeyUsage EASG product cert attribute"
          ::= { endptEASGProdCertAttributes 8 } 
      
endptEASGProdCertAltname  OBJECT-TYPE
          SYNTAX        DisplayString (SIZE(0..255))
          MAX-ACCESS    read-only
          STATUS        current
          DESCRIPTION   "Altname name of EASG product certificate"
          ::= { endptEASGProdCertAttributes 9 } 
          
endptEASGProdCertFingerprint  OBJECT-TYPE
          SYNTAX        DisplayString (SIZE(0..255))
          MAX-ACCESS    read-only
          STATUS        current
          DESCRIPTION   "Sha1Hash of EASG product cert (Displayed by HEX string)"
          ::= { endptEASGProdCertAttributes 10 }          
                    
endptEASGProdCertBasicContraints     OBJECT-TYPE
          SYNTAX        DisplayString (SIZE(0..255))
          MAX-ACCESS    read-only
          STATUS  current
          DESCRIPTION  "BasicConstrains EASG product cert attribute"
          ::= { endptEASGProdCertAttributes 11 }

endptEASGStatus          OBJECT-TYPE
            SYNTAX      INTEGER
            MAX-ACCESS  read-only
            STATUS      current
            DESCRIPTION "Report the EASG status"           
            ::= { endptID 173 } 

endptEASGSiteCerts          OBJECT-TYPE
            SYNTAX      INTEGER
            MAX-ACCESS  read-only
            STATUS      current
            DESCRIPTION "Report the EASG site certs"           
            ::= { endptID 174 } 

endptEASGSiteCertsWarningDays        OBJECT-TYPE
            SYNTAX      INTEGER
            MAX-ACCESS  read-only
            STATUS      current
            DESCRIPTION "Report the EASG site certs warning days"           
            ::= { endptID 175 } 

endptMaxTrustCerts      OBJECT-TYPE
            SYNTAX      INTEGER
            MAX-ACCESS  read-only
            STATUS      current
            DESCRIPTION "Report the maximum number of trusted certificates"
            ::= { endptID 176 } 

endptAUDIOALERTMODE      OBJECT-TYPE
            SYNTAX      INTEGER
            MAX-ACCESS  read-only
            STATUS      current
            DESCRIPTION "Audio alerting mode"
            ::= { endptID 177 } 

endptHEADSETOPERATIONALMODE      OBJECT-TYPE
            SYNTAX      INTEGER
            MAX-ACCESS  read-only
            STATUS      current
            DESCRIPTION "Headset operational mode"
            ::= { endptID 178 } 

endptBACKGROUNDIMAGE OBJECT-TYPE
          SYNTAX DisplayString
          MAX-ACCESS    read-only
          STATUS        current
          DESCRIPTION   "Specifies a list of background images"
          ::= { endptID 179 }

endptBACKGROUNDIMAGEDISPLAY OBJECT-TYPE
          SYNTAX DisplayString
          MAX-ACCESS    read-only
          STATUS        current
          DESCRIPTION   "The background to display"
          ::= { endptID 180 }

endptBACKGROUNDIMAGESELECTABLE OBJECT-TYPE
          SYNTAX INTEGER
          MAX-ACCESS    read-only
          STATUS        current
          DESCRIPTION   "1 or 0. If 1, then the user is allowed to choose a background"
          ::= { endptID 181 }

endptSCREENSAVERIMAGE OBJECT-TYPE
          SYNTAX DisplayString
          MAX-ACCESS    read-only
          STATUS        current
          DESCRIPTION   "Specifies a list of screensaver images"
          ::= { endptID 182 }

endptSCREENSAVERIMAGEDISPLAY OBJECT-TYPE
          SYNTAX DisplayString
          MAX-ACCESS    read-only
          STATUS        current
          DESCRIPTION   "Specifies the administrator choice of screensaver image"
          ::= { endptID 183 }

endptSCREENSAVERIMAGESELECTABLE OBJECT-TYPE
          SYNTAX INTEGER
          MAX-ACCESS    read-only
          STATUS        current
          DESCRIPTION   "1 or 0. If 1, then the user is allowed to choose a screensaver"
          ::= { endptID 184 }

endptSCREENSAVERCLOCKENABLE OBJECT-TYPE
          SYNTAX INTEGER
          MAX-ACCESS    read-only
          STATUS        current
          DESCRIPTION   "1 or 0. If 1, then screensaver shows a clock"
          ::= { endptID 185 }

endptSCREENSAVERIMAGEAVAILABLE OBJECT-TYPE
          SYNTAX DisplayString
          MAX-ACCESS    read-only
          STATUS        current
          DESCRIPTION   "Available screensaver images"
          ::= { endptID 186 }

endptBACKGROUNDIMAGEAVAILABLE OBJECT-TYPE
          SYNTAX DisplayString
          MAX-ACCESS    read-only
          STATUS        current
          DESCRIPTION   "Available background images"
          ::= { endptID 187 }

endptACOUSTICEXPOSUREPROTECTMODE OBJECT-TYPE
          SYNTAX      INTEGER
          MAX-ACCESS  read-only
          STATUS      current
          DESCRIPTION "This variable returns the current Acoustic Exposure Protection Mode.
          This is a User Specific parameter.
          '0' Default
          '1' Off
          '2' Dynamic
          '3' 4 hours
          '4' 8 hours"
          ::= { endptID 188 }

endptBACKGROUNDIMAGESECONDARY OBJECT-TYPE
          SYNTAX DisplayString
          MAX-ACCESS    read-only
          STATUS        current
          DESCRIPTION   "A roster of user background images for secondary display"
          ::= { endptID 189 }

endptBACKGROUNDIMAGEDISPLAYSECONDARY OBJECT-TYPE
          SYNTAX DisplayString
          MAX-ACCESS    read-only
          STATUS        current
          DESCRIPTION   "The background to display for secondary display"
          ::= { endptID 190 }

endptBACKGROUNDIMAGESELECTABLESECONDARY OBJECT-TYPE
          SYNTAX INTEGER
          MAX-ACCESS    read-only
          STATUS        current
          DESCRIPTION   "1 or 0. If 1, then the user is allowed to choose a background for secondary display"
          ::= { endptID 191 }

endptBACKGROUNDIMAGEAVAILABLESECONDARY OBJECT-TYPE
          SYNTAX DisplayString
          MAX-ACCESS    read-only
          STATUS        current
          DESCRIPTION   "Available background images for secondary display"
          ::= { endptID 192 }

endptSCREENSAVERIMAGESECONDARY OBJECT-TYPE
          SYNTAX DisplayString
          MAX-ACCESS    read-only
          STATUS        current
          DESCRIPTION   "A roster of user screensaver images"
          ::= { endptID 193 }

endptSCREENSAVERIMAGEDISPLAYSECONDARY OBJECT-TYPE
          SYNTAX DisplayString
          MAX-ACCESS    read-only
          STATUS        current
          DESCRIPTION   "The screensaver to display"
          ::= { endptID 194 }

endptSCREENSAVERIMAGESELECTABLESECONDARY OBJECT-TYPE
          SYNTAX INTEGER
          MAX-ACCESS    read-only
          STATUS        current
          DESCRIPTION   "1 or 0. If 1, then the user is allowed to choose a screensaver"
          ::= { endptID 195 }

endptSCREENSAVERIMAGEAVAILABLESECONDARY OBJECT-TYPE
          SYNTAX DisplayString
          MAX-ACCESS    read-only
          STATUS        current
          DESCRIPTION   "Available screensaver images"
          ::= { endptID 196 }

endptSECONDARYDISPLAYBRIGHTNESS  OBJECT-TYPE
          SYNTAX      INTEGER
          MAX-ACCESS  read-only
          STATUS      current
          DESCRIPTION "Display Brightness setting for secondary display. 
          This variable returns the value of the display brightness setting  
          in memory. Range is 0-5, with 4 the default."
          ::= { endptID 197 }

endptPHONESCREENMODE  OBJECT-TYPE
          SYNTAX      INTEGER
          MAX-ACCESS  read-only
          STATUS      current
          DESCRIPTION "Specifies the default layout of the main phone's screen which can be either full width or half width (two columns)
                       Range is 0-3, with 0 as default, where
                       '0' Full width, adjustable by the user
                       '1' Half width, adjustable by the user
                       '2' Full width, forced
                       '3' Half width, forced"
          ::= { endptID 198 }

endptRINGREMINDERRINGTONE OBJECT-TYPE
          SYNTAX DisplayString
          MAX-ACCESS    read-only
          STATUS        current
          DESCRIPTION   "Defines the ringtone that will be played when there is some call on hold and server notifies about it."
          ::= { endptID 199 }

endptENABLEGDPRMODE  OBJECT-TYPE
          SYNTAX      INTEGER
          MAX-ACCESS  read-only
          STATUS      current
          DESCRIPTION "1 if the GDPR (Global data protection regulation) Mode feature is enabled and 0 otherwise, default is 0."
          ::= { endptID 200 }

endptENABLERFC5922  OBJECT-TYPE
          SYNTAX      INTEGER
          MAX-ACCESS  read-only
          STATUS      current
          DESCRIPTION "Enable or disable checking the SIP server certificate for RFC5922 compliance (SIP domain match found in CN or Subject Alternate Name)."
          ::= { endptID 201 }

endptSYSLOGLEVEL    OBJECT-TYPE
          SYNTAX      INTEGER
          MAX-ACCESS  read-only
          STATUS      current
          DESCRIPTION "Remote logging level."
          ::= { endptID 202 }

endptADMINTIMEFORMAT  OBJECT-TYPE
          SYNTAX      INTEGER
          MAX-ACCESS  read-only
          STATUS      current
          DESCRIPTION "Admin Time Format setting. This variable returns:
          0 - for am/pm format (default)
          1 - for 24h format
          2 - for am/pm format (forced)
          3 - for 24h format (forced). 
          When ADMINTIMEFORMAT is 0 or 1, UI 'Time format' has precedence over ADMINTIMEFORMAT, meaning a user can change the time format in UI.
          When ADMINTIMEFORMAT is 2 or 3, ADMINTIMEFORMAT applies and there is no UI option to change the time format. 
          ADMINTIMEFORMAT is not applicable in Aura and IPO CCMS environments"                        
          ::= { endptID 203 }



endptMaintenance        OBJECT IDENTIFIER ::= { avayaSparkMIB 3 }
endptAPPstat    OBJECT-TYPE 
                    SYNTAX      INTEGER  
                    MAX-ACCESS  read-only
                    STATUS      current
                    DESCRIPTION "Application/Library software package download flag. 
                        This variable returns:
                        '0' if the value of APPNAME is null. 
                        '1' if the most recent attempt to download a new Application/Library software package was not successful.
                        '2' if the most recent attempt to download a new Application/Library software package was successful, but the file was too large. 
                        '3' if the most recent attempt to download a new Application/Library software package was successful, but the file type was incorrect. 
                        '4' if the most recent attempt to download a new Application/Library software package was successful, but files were missing, had the wrong file type, or had invalid signatures. 
                        '5' if the most recent attempt to download a new Application/Library software package was successful, but was not valid for the telephone hardware. 
                        '6' if the most recent attempt to download a new Application/Library software package was successful, but it was not compatible with the new Kernel/RFS software package.
                        '7' if the most recent attempt to download a new Application/Library software package was successful, but it was not compatible with the existing Kernel/RFS software package.
                        '8' if the most recent attempt to download a new Application/Library software package was successful, but the existing Kernel/RFS software package was not compatible with it.
                        '9' if the most recent attempt to download, store and install a new Application/Library software package was successful.
                        '10' if there was a failure to write software file to flash (Supported by  phones with HWVERS 3 and up as conveyed by endptHWVER).
                        '11' if there was a failure of signature verification for BootA (Supported by  phones with HWVERS 3 and up as conveyed by endptHWVER).
                        '12' if there was a failure of signature verification for BootB (Supported by  phones with HWVERS 3 and up as conveyed by endptHWVER).;
                        '13' if there was a failure of signature verification for system RFS (Supported by  phones with HWVERS 3 and up as conveyed by endptHWVER).
                        '14' if a new firmware file was found to have the same software version as the one installed (identical software) 
                        - no upgrade required (Supported by  phones with HWVERS 3 and up as conveyed by endptHWVER).
                        "
            ::= { endptMaintenance 1 }   
            
endptRFSstat    OBJECT-TYPE 
                    SYNTAX      INTEGER  
                    MAX-ACCESS  read-only
                    STATUS      current
                    DESCRIPTION "Kernel/RFS software package download flag. 
                        This variable returns '0' if the value of RFSNAME is null. This
            variable returns '1' if the most recent attempt to download 
                        a new Kernel/RFS software package was not successful.
            This variable returns '2' if the most recent attempt to download a 
                        new Kernel/RFS software package was successful, 
                        but the file was too large. This variable returns 3 if the most 
                        recent attempt to download a new Kernel/RFS software package was 
                        successful, but the file type was incorrect. This variable returns 4 if the 
                        most recent attempt to download a new Kernel/RFS software package 
                        was successful, but files were missing, had the wrong file 
                        type, or had invalid signatures. This variable returns 5 if the most recent 
                        attempt to download a new Kernel/RFS software package was successful, 
                        but was not valid for the telephone hardware. This variable returns 6 if the 
                        most recent attempt to download a new Kernel/RFS software package 
                        was successful, but it was not compatible with the new Application/Library software package.
                        This variable returns 7 if the most recent attempt to download a new 
                        Kernel/RFS software package was successful, but it was 
                        not compatible with the existing Application/Library software package.
                        This variable returns 8 if the most recent attempt to download a new 
                        Kernel/RFS software package was successful, but the 
                        existing Application/Library software package was not compatible with it.
                        This variable returns 9 if the most recent attempt to download, store 
                        and install a new  Kernel/RFS software package was successful.
                        This MIB item is not applicable for phones with HWVERS 3 and up as conveyed by endptHWVER.
                        "
            ::= { endptMaintenance 2 }
endptUPGRADESTAT OBJECT-TYPE 
                    SYNTAX      INTEGER  
                    MAX-ACCESS  read-only
                    STATUS      current
                    DESCRIPTION "Script loading status flag. This variable
                        returns '0' if a 96x1Supgrade.txt file was successfully 
                        obtained and interpreted since the last power-up or  
                        reset. This variable returns '1' if the file was  
                        successfully obtained but NOT successfully interpreted  
                        since the last power-up or reset. This variable returns 
                        '2' if the file was NOT successfully obtained since the 
                        last power-up or reset."
                    ::= { endptMaintenance 3 }
endptRecentLogTable  OBJECT-TYPE
          SYNTAX SEQUENCE OF EndptRecentLogEntry
          MAX-ACCESS    not-accessible
          STATUS        current
          DESCRIPTION   "Each entry is one of up to 500 syslog event 
            messages added since last reset or power-up, each of 
            which has severity code less than the value of the  
                        administered log level and which matchs for level 
                        'warning' and below to the administered log categories.
            Entries are in chronological order, oldest first."
          ::= { endptMaintenance 4 }
endptRecentLogEntry OBJECT-TYPE
          SYNTAX EndptRecentLogEntry
          MAX-ACCESS    not-accessible
          STATUS        current
          DESCRIPTION   "Each entry is one of up to 500 syslog event 
            messages added since last reset or power-up, each of 
            which has severity code less than the value of the  
                        administered log level and which matchs for level 
                        'warning' and below to the administered log categories.
            Entries are in chronological order, oldest first."
          INDEX     { endptRecentLogIndex }
          ::= { endptRecentLogTable 1 }
EndptRecentLogEntry     ::= 
            SEQUENCE  {
                    endptRecentLogIndex
                    INTEGER,
                    endptRecentLogText
                       DisplayString
                }
endptRecentLogIndex     OBJECT-TYPE
        SYNTAX  INTEGER
            MAX-ACCESS  not-accessible
            STATUS  current
            DESCRIPTION
                    "log index."
            ::= { endptRecentLogEntry 1 }

endptRecentLogText  OBJECT-TYPE
          SYNTAX        DisplayString (SIZE(0..255))
          MAX-ACCESS    read-only
          STATUS        current
          DESCRIPTION   "Syslog event message."
          ::= { endptRecentLogEntry 2 } 
endptResetLogTable   OBJECT-TYPE
          SYNTAX SEQUENCE OF EndptResetLogEntry
          MAX-ACCESS    not-accessible
          STATUS        current
          DESCRIPTION   "Each entry is one of up to 500 syslog event 
            messages added before the last reset or power-up, each 
            of which has severity code less than the value of the  
                        administered log level and which matchs for level 
                        'warning' and below to the administered log categories. 
            Entries are in chronological order, oldest first."
          ::= { endptMaintenance 5 }
endptResetLogEntry     OBJECT-TYPE
          SYNTAX EndptResetLogEntry
          MAX-ACCESS    not-accessible
          STATUS        current
          DESCRIPTION   "Each entry is one of up to 500 syslog event 
            messages added before the last reset or power-up, each  
            of which has severity code less than the value of the  
                        administered log level and which matchs for level 
                        'warning' and below to the administered log categories. 
            Entries are in chronological order, oldest first."
          INDEX     { endptResetLogIndex }
              ::= { endptResetLogTable 1 }
EndptResetLogEntry      ::= 
                SEQUENCE {
                    endptResetLogIndex
                    INTEGER,
                    endptResetLogText
                        DisplayString
                }
endptResetLogIndex  OBJECT-TYPE
        SYNTAX  INTEGER
            MAX-ACCESS  not-accessible
            STATUS  current
            DESCRIPTION
                    "log index."
            ::= { endptResetLogEntry 1 }
endptResetLogText   OBJECT-TYPE
          SYNTAX        DisplayString (SIZE(0..255))
          MAX-ACCESS    read-only
          STATUS        current
          DESCRIPTION   "Syslog event message."
          ::= { endptResetLogEntry 2 }  
endptStartupLogTable   OBJECT-TYPE
          SYNTAX SEQUENCE OF EndptStartupLogEntry
          MAX-ACCESS    not-accessible
          STATUS        current
          DESCRIPTION   "Each entry is one of up to 75 syslog event 
            messages added before the last reset or power-up, each 
            of which has severity code less than the value of the  
                        administered log level and which matchs for level 
                        'warning' and below to the administered log categories. 
            Entries are in chronological order, oldest first."
          ::= { endptMaintenance 6 }
endptStartupLogEntry       OBJECT-TYPE
          SYNTAX EndptStartupLogEntry
          MAX-ACCESS    not-accessible
          STATUS        current
          DESCRIPTION   "Each entry is one of up to 75 syslog event 
            messages added before the last reset or power-up, each  
            of which has severity code less than the value of the  
                        administered log level and which matchs for level 
                        'warning' and below to the administered log categories. 
            Entries are in chronological order, oldest first."
          INDEX     { endptStartupLogIndex }
              ::= { endptStartupLogTable 1 }
EndptStartupLogEntry        ::= 
                SEQUENCE {
                    endptStartupLogIndex
                    INTEGER,
                    endptStartupLogText
                        DisplayString
                }
endptStartupLogIndex    OBJECT-TYPE
        SYNTAX  INTEGER
            MAX-ACCESS  not-accessible
            STATUS  current
            DESCRIPTION
                    "log index."
            ::= { endptStartupLogEntry 1 }
endptStartupLogText OBJECT-TYPE
          SYNTAX        DisplayString (SIZE(0..255))
          MAX-ACCESS    read-only
          STATUS        current
          DESCRIPTION   "Syslog event message."
          ::= { endptStartupLogEntry 2 }    
endptRESTARTCOUNTER OBJECT-TYPE 
                    SYNTAX      INTEGER  
                    MAX-ACCESS  read-only
                    STATUS      current
                    DESCRIPTION "Counter of restarts after power-up. This 
                        variable is reset to 0 after each power-up. Subsequent 
                        restarts increment the variable by one 
                        (but not the initial start-up after power-up)."
            ::= { endptMaintenance 7 }
            
endptAUTHCTRLSTAT OBJECT-TYPE
                    SYNTAX      INTEGER  
                    MAX-ACCESS  read-only
                    STATUS      current
                    DESCRIPTION "Enhanced debugging capabilities mode. This MIB item reflects the value of AUTHCTRLSTAT. If 0 (default), then
                    the enhanced debugging capabilities mode is disabled. if 1, then the enhanced debugging capabilities mode is enabled.
                    This mode shall ALWAYS be disabled, unless Avaya Technician requests to enable it for better debugging of the phone."
            ::= { endptMaintenance 8 }

endptSSHSTATUS      OBJECT-TYPE
                    SYNTAX      INTEGER  
                    MAX-ACCESS  read-only
                    STATUS      current
                    DESCRIPTION "SSH status flag. This variable returns '0' if SSH is disabled; '1' if it is enabled, but
                    there is no active connections and '2' if there is an established connection"
                    ::= { endptMaintenance 9 }

endptApps    OBJECT IDENTIFIER ::= { avayaSparkMIB 4 }
endptEXTAPPIFPORT  OBJECT-TYPE
                    SYNTAX      INTEGER 
                    MAX-ACCESS  read-only
                    STATUS      current
                    DESCRIPTION "External Application Interface port. This 
                        variable returns the port number of endpoint's XML 
                        interface for external applications. Default is 6225."  
                    ::= { endptApps 1 }
endptEXTAPPIFSTATUS  OBJECT-TYPE
                    SYNTAX      INTEGER 
                    MAX-ACCESS  read-only
                    STATUS      current
                    DESCRIPTION "External Application Interface status. This 
                        variable returns 1 if endpoint's XML interface for 
                        external applications is a TCP interface, and 2 
                        if it is a TLS over TCP interface. Default is 1."  
                    ::= { endptApps 2 }
endptEXTAPPIFTYPE  OBJECT-TYPE
                    SYNTAX      INTEGER 
                    MAX-ACCESS  read-only
                    STATUS      current
                    DESCRIPTION "External Application Interface type. This 
                        variable returns 0 if endpoint's XML interface for 
                        external applications is disabled, else 1."  
                    ::= { endptApps 3 }
endptAUDIOPATH  OBJECT-TYPE
                    SYNTAX      INTEGER 
                    MAX-ACCESS  read-only
                    STATUS      current
                    DESCRIPTION "User audio path.  This variable returns 0 if 
            the telephone does not support a 2-way speaker or does 
                        not have a headset jack; 1 if the user audio path is  
                        with the speakerphone, and 2 if the user audio path is 
                        with the headset."  
                    ::= { endptApps 4 }
endptENHDIALSTAT  OBJECT-TYPE
                    SYNTAX      INTEGER 
                    MAX-ACCESS  read-only
                    STATUS      current
                    DESCRIPTION "Enhanced Local Dialing status.  This variable 
            returns 0 if the Enhanced Local Dialing status is
                        off/disabled, 1 if enhanced local dialing is partially 
                        enabled (does NOT apply for dialing from contatcs), 
                        2 if enhanced dialing is fully enabled, and 
                        3 if enhanced local dialing is fully enabled 
                        for 3PCC environment"                     
                    ::= { endptApps 5 }
endptEXCHANGESRVR  OBJECT-TYPE
                    SYNTAX      DisplayString
                    MAX-ACCESS  read-only
                    STATUS      current
                    DESCRIPTION "Exchange server addresses. This variable  
            returns zero or more MS Exchange (TM) server addresses 
                        for retrieval of calendar or contact data, in dotted 
                        decimal or DNS format."  
                    ::= { endptApps 6 }
endptEXCHANGESRVRINUSE  OBJECT-TYPE
                    SYNTAX      IpAddress
                    MAX-ACCESS  read-only
                    STATUS      current
                    DESCRIPTION "Exchange server IP address.  This variable  
            returns a 4-octet IP address for the MS Exchange (TM) 
                        server used to retrieve calendar or contact data 
                        (all zeros if no server used)."  
                    ::= { endptApps 7 }
endptMMSRVR     OBJECT-TYPE
                    SYNTAX      DisplayString
                    MAX-ACCESS  read-only
                    STATUS      current
                    DESCRIPTION "Modular Messaging server addresses. This 
                        variable is a placeholder for future use."  
                    ::= { endptApps 8 }
endptMMSRVRINUSE  OBJECT-TYPE
                    SYNTAX      IpAddress
                    MAX-ACCESS  read-only
                    STATUS      current
                    DESCRIPTION "Modular Messaging server IP address. This 
                        variable returns a 4-octet IP address for the Modular 
                        messaging server (all zeros if no server used)."  
                    ::= { endptApps 9 }
endptMMPORT     OBJECT-TYPE
                    SYNTAX      INTEGER 
                    MAX-ACCESS  read-only
                    STATUS      current
                    DESCRIPTION "Modular Messaging server port. This variable
            is a placeholder for future use. It currently 
                        returns '-1'."  
                    ::= { endptApps 10 }
endptWMLEXCEPT    OBJECT-TYPE
                    SYNTAX      DisplayString
                    MAX-ACCESS  read-only
                    STATUS      current
                    DESCRIPTION "Web Proxy Server Exception List. This 
                       variable returns a string specifying a list of one or 
                       more HTTP proxy server Exception domains, separated by 
                       commas with no intervening spaces. Used by the Web
                       Browser application."  
                    ::= { endptApps 11 }
endptWMLHOME      OBJECT-TYPE
                    SYNTAX      DisplayString
                    MAX-ACCESS  read-only
                    STATUS      current
                    DESCRIPTION "Web application URL. This variable returns
                        a URL of the Home page for the Web Browser application."  
                    ::= { endptApps 12 }
endptWMLIDLETIME  OBJECT-TYPE
                    SYNTAX      INTEGER
                    MAX-ACCESS  read-only
                    STATUS      current
                    DESCRIPTION "Web Idle Timer. This variable returns the number
                       of minutes, from 1 to 60 inclusive, of idle activity on the
                       telephone before the Web Idle Timer URI is displayed."  
                    ::= { endptApps 13 }
endptWMLIDLEURI   OBJECT-TYPE
                    SYNTAX      DisplayString
                    MAX-ACCESS  read-only
                    STATUS      current
                    DESCRIPTION "Web Idle Timer URI. This variable returns the
                        URI of the WML page displayed after the Web 
                        Idle Timer expires."  
                    ::= { endptApps 14 }
endptWMLPORT      OBJECT-TYPE
                    SYNTAX      INTEGER
                    MAX-ACCESS  read-only
                    STATUS      current
                    DESCRIPTION "Web Browser application TCP port. This variable 
                        returns an integer specifying the TCP port used for  
                        the Web proxy server.  Used by the Web
                        Browser application."  
                    ::= { endptApps 15 }
endptWMLPROXY     OBJECT-TYPE
                    SYNTAX      DisplayString
                    MAX-ACCESS  read-only
                    STATUS      current
                    DESCRIPTION "Web Proxy Server. This variable returns
                        an IP addresses, in dotted-decimal or DNS format, of an  
                        HTTP proxy server.  Used by the Web Browser application."  
                    ::= { endptApps 16 }
endptAGENTTONE     OBJECT-TYPE
                    SYNTAX      INTEGER
                    MAX-ACCESS  read-only
                    STATUS      current
                    DESCRIPTION "Agent tone. This variable is a
                        placeholder for future use."
                    ::= { endptApps 17 }
endptPHNDSPLYALERT     OBJECT-TYPE
                    SYNTAX      INTEGER
                    MAX-ACCESS  read-only
                    STATUS      current
                    DESCRIPTION "Display call on ringing option. This variable
                        is a placeholder for future use."
                    ::= { endptApps 18 }
endptPROVIDEEDITEDDIALING     OBJECT-TYPE
                    SYNTAX      INTEGER
                    MAX-ACCESS  read-only
                    STATUS      current
                    DESCRIPTION "Specifies whether to show a list or one number on Redial Softkey.
                    Ranges 0 - 2. 
                    1 is default"
                    ::= { endptApps 19 }
endptFAVORITES     OBJECT-TYPE
                    SYNTAX      DisplayString
                    MAX-ACCESS  read-only
                    STATUS      current
                    DESCRIPTION "Represents a list of favorites.
                        This variable returns a string representing the list of 
                        favorites selected by the user." 
                    ::= { endptApps 20 }
endptPROVIDETRANSFERTYPE     OBJECT-TYPE
                    SYNTAX      INTEGER
                    MAX-ACCESS  read-only
                    STATUS      current
                    DESCRIPTION "When the AVAYAENVIRONMENT variable is 0, 
                        this parameter controls the display of the transfer type option 
                        in the A menu. This variable returns 0 if the option is not shown 
                        and 1 if it is shown, allowing the user to choose the 
                        type of transfer."
                    ::= { endptApps 21 }
endptCALLTRANSFERMODE     OBJECT-TYPE
                    SYNTAX      INTEGER
                    MAX-ACCESS  read-only
                    STATUS      current
                    DESCRIPTION "When the AVAYAENVIRONMENT variable is 0, 
                        this parameter controls the default transfer mode. 
                        This variable returns 0 if the mode is attended and 
                        1 if the mode is unattended."
                    ::= { endptApps 22 }
endptCNGLABEL       OBJECT-TYPE
                    SYNTAX      INTEGER
                    MAX-ACCESS  read-only
                    STATUS      current
                    DESCRIPTION "Controls the ability to personalize button labels 
                        displayed to the user.
                        This variable returns 0 if the user cannot personalize the labels 
                        and 1 if the user can personalize the labels."
                    ::= { endptApps 23 }
endptQKLOGINSTAT    OBJECT-TYPE
                    SYNTAX      INTEGER
                    MAX-ACCESS  read-only
                    STATUS      current
                    DESCRIPTION "Controls whether a password must always be entered manually.
                        This variable returns 0 if manual password entry is mandatory
                        and 1 if the user can perform a quick login by pressing the continue 
                        soft key on the Login screen to accept the current password value."
                    ::= { endptApps 24 }
endptPUSHCAP  OBJECT-TYPE
                    SYNTAX      DisplayString                  
                    MAX-ACCESS  read-only
                    STATUS      current
                    DESCRIPTION "Push capabilities. This variable returns a 
                        5-digit integer specifying the phone administration for phoneXML, 
                        audio transmit, audio receive, display (web), and Top Line pushes, respectively.
                        The valid digits are 0 (Disabled), 1 (barge-in only ypushes of the given
                        type Enabled) and 2 (both barge-in and normal pushes of the given
                        type Enabled).  The default is 00000."
                    ::= { endptApps 25 }
endptPUSHPORT  OBJECT-TYPE
                    SYNTAX      INTEGER
                    MAX-ACCESS  read-only
                    STATUS      current
                    DESCRIPTION "Push listening port. This variable returns an 
                       integer specifying the TCP listening port most recently 
                        used for the HTTP server.."
                    ::= { endptApps 26 }
endptSUBSCRIBELIST    OBJECT-TYPE
                    SYNTAX      DisplayString 
                    MAX-ACCESS  read-only
                    STATUS      current
                    DESCRIPTION "96xx Web push subscription list. This 
                       variable returns a string containing one or more fully 
                       qualified URLs to which the phone's Browser application 
                       subscribes for potential pushed content."
                    ::= { endptApps 27 }
endptTPSLIST    OBJECT-TYPE
                    SYNTAX      DisplayString 
                    MAX-ACCESS  read-only
                    STATUS      current
                    DESCRIPTION "96xx Web Trusted Push Server list. This 
                       variable returns a string containing one or more domains 
                       and paths in DNS format, used to determine for 
                       validation of push requests."
                    ::= { endptApps 28 }
endptCURRENTCONTENT    OBJECT-TYPE
                    SYNTAX      DisplayString 
                    MAX-ACCESS  read-only
                    STATUS      current
                    DESCRIPTION "96xx URL of the customization file for the Home 
                       Screen. This variable returns a string containing the location 
                       of the XML file that is used to defined the contents of the Home 
                       screen."
                    ::= { endptApps 29 }
endptDISPLAYNAMENUMBER  OBJECT-TYPE
                    SYNTAX      INTEGER
                    MAX-ACCESS  read-only
                    STATUS      current
                    DESCRIPTION "Controls whether both the name and the number are displayed
                       for an incoming call. This variable returns 0 when only the name is shown.
                       The variable returns 1 when both the name and number are shown."
                    ::= { endptApps 30 }
endptPROVIDEEXCHANGECALENDAR  OBJECT-TYPE
                    SYNTAX      INTEGER
                    MAX-ACCESS  read-only
                    STATUS      current
                    DESCRIPTION "Flag to define whether or not menu item(s) for MS Exchange(tm) Calendar 
                       integration are provided to user. This variable returns 0 when the menu is
                       not provided to the user and 1 when the menu is provided. The default is 1."
                    ::= { endptApps 31 }
endptEXCHANGESERVERLIST  OBJECT-TYPE
                    SYNTAX      DisplayString
                    MAX-ACCESS  read-only
                    STATUS      current
                    DESCRIPTION "List of Microsoft Exchange server IP or DNS addresses.
                       This variable returns zero or more IP addresses in dotted decimal or DNS name format, 
                       separated by commas without any intervening spaces."
                    ::= { endptApps 32 }
endptEXCHANGESERVERINUSE  OBJECT-TYPE
                    SYNTAX      DisplayString
                    MAX-ACCESS  read-only
                    STATUS      current
                    DESCRIPTION "The Microsoft Exchange server currently used.
                       This variable returns one IP address in dotted decimal format."
                    ::= { endptApps 33 }
endptUSEEXCHANGECALENDAR  OBJECT-TYPE
                    SYNTAX      INTEGER
                    MAX-ACCESS  read-only
                    STATUS      current
                    DESCRIPTION "Activate or deactivate usage of calendar on a Microsoft Exchange Server.
                       This variable returns 0 when the calendar is disabled and
                       1 when the calendar is enabled. The default is 0."
                    ::= { endptApps 34 }
endptEXCHANGEUSERDOMAIN  OBJECT-TYPE
                    SYNTAX      DisplayString
                    MAX-ACCESS  read-only
                    STATUS      current
                    DESCRIPTION "The user domain for a Microsoft Exchange Server.
                       This variable returns a string with the user domain."
                    ::= { endptApps 35 }
endptEXCHANGEUSERACCOUNT  OBJECT-TYPE
                    SYNTAX      DisplayString
                    MAX-ACCESS  read-only
                    STATUS      current
                    DESCRIPTION "The user's account for the Microsoft Exchange Server
                       This variable returns a string with the user's account."
                    ::= { endptApps 36 }
endptENABLEEXCHANGEREMINDER  OBJECT-TYPE
                    SYNTAX      INTEGER
                    MAX-ACCESS  read-only
                    STATUS      current
                    DESCRIPTION "Controls whether Exchange popup reminder notifications are enabled.
                       This variable returns 0 when reminders are disabled and
                       1 when reminders are enabled. The default is 0."
                    ::= { endptApps 37 }
endptEXCHANGEREMINDERTIME  OBJECT-TYPE
                    SYNTAX      INTEGER
                    MAX-ACCESS  read-only
                    STATUS      current
                    DESCRIPTION "Controls how far in advance the user wants to get the reminder for an appointment.
                       This variable has a range of 0 to 60 minutes. The default is 5 minutes."
                    ::= { endptApps 38 }
endptEXCHANGESNOOZETIME  OBJECT-TYPE
                    SYNTAX      INTEGER
                    MAX-ACCESS  read-only
                    STATUS      current
                    DESCRIPTION "Controls how long in minutes for the Reminder to reappear 
                       after it has been snoozed (temporally dismissed) by the user.
                       This variable returns 0 when only the name is shown.
                       This variable has a range of 0 to 60 minutes. The default is 5 minutes."
                    ::= { endptApps 39 }
endptEXCHANGEREMINDERTONE  OBJECT-TYPE
                    SYNTAX      INTEGER
                    MAX-ACCESS  read-only
                    STATUS      current
                    DESCRIPTION "Enables or disables the generation of a reminder tone (error beep) 
                       that will be played when the Reminder popup appears.
                       This variable returns 0 when the tone is disabled and
                       1 when the tone is enabled."
                    ::= { endptApps 40 }
endptEXCHANGENOTIFYSUBSCRIPTIONPERIOD  OBJECT-TYPE
                    SYNTAX      INTEGER
                    MAX-ACCESS  read-only
                    STATUS      current
                    DESCRIPTION "Controls the resynchronization interval with the Exchange server.
                       This variable returns a value between 0 and 3600 seconds.
                       The default is 180 seconds."
                    ::= { endptApps 41 }
endptENABLEPHONELOCK  OBJECT-TYPE
                    SYNTAX      INTEGER
                    MAX-ACCESS  read-only
                    STATUS      current
                    DESCRIPTION "Enables or disables the local station lock feature.
                       This variable returns 0 when the feature is disabled and
                       1 when the feature is enabled. The default is 0."
                    ::= { endptApps 42 }
endptPHONELOCKIDLETIME  OBJECT-TYPE
                    SYNTAX      INTEGER
                    MAX-ACCESS  read-only
                    STATUS      current
                    DESCRIPTION "Controls the idle time for the Phone Lock feature.
                       This variable returns 0 when the phone does not lock.
                       The variable returns 1  to 999 to show the number of minutes of 
                       idle time before the phone locks. The default is 0."
                    ::= { endptApps 43 }
endptAUDIOSTHS   OBJECT-TYPE 
                    SYNTAX      INTEGER  
                    MAX-ACCESS  read-only
                    STATUS      current
                    DESCRIPTION "Handset sidetone settings
                        This variable returns:
                        '0'    NORMAL level for most users (default)
                        '1'    three levels softer than NORMAL
                        '2'    OFF (inaudible)
                        '3'    one level softer than NORMAL
                        '4'    two levels softer than NORMAL
                        '5'    four levels softer than NORMAL
                        '6'    five levels softer than NORMAL
                        '7'    six levels softer than NORMAL
                        '8'    one level louder than NORMAL
                        '9'    two levels louder than NORMAL
                        "
            ::= { endptApps 44 }
endptAUDIOSTHD   OBJECT-TYPE 
                    SYNTAX      INTEGER  
                    MAX-ACCESS  read-only
                    STATUS      current
                    DESCRIPTION "Headset sidetone settings
                        This variable returns:
                        '0'    NORMAL level for most users (default)
                        '1'    three levels softer than NORMAL
                        '2'    OFF (inaudible)
                        '3'    one level softer than NORMAL
                        '4'    two levels softer than NORMAL
                        '5'    four levels softer than NORMAL
                        '6'    five levels softer than NORMAL
                        '7'    six levels softer than NORMAL
                        '8'    one level louder than NORMAL
                        '9'    two levels louder than NORMAL
                        "
            ::= { endptApps 45 }
endptAUDIOENV   OBJECT-TYPE 
                    SYNTAX      INTEGER  
                    MAX-ACCESS  read-only
                    STATUS      current
                    DESCRIPTION " Audio Environment Index
                        Enables to customize the telephone's audio performance.
                        The range is from 0 to 299. The default is 0.
                        "
            ::= { endptApps 46 }

endptHEADSETGAIN    OBJECT-TYPE
                    SYNTAX      INTEGER
                    MAX-ACCESS  read-only
                    STATUS      current
                    DESCRIPTION "This variable returns a value of user-adjusted TX gain for a headset."                        
                    ::= { endptApps 47 }
endptENABLEOPUS OBJECT-TYPE
                    SYNTAX      INTEGER  
                    MAX-ACCESS  read-only
                    STATUS      current
                    DESCRIPTION "Specifies whether the OPUS codec is enabled.
                        Value Operation
                        #0 Disabled
                        #1 Enabled WIDEBAND_20K (default value).
                        #2 Enabled NARROWBAND_16K
                        #3 Enabled NARROWBAND_12K
                        #4 Enabled SUPER_WIDEBAND (J189 only)
                        This parameter is supported by:
                        Avaya Vantage Connect Application SIP R1.0.0.1 and later; supported in both Aura and IPO environments. 
                        R2.0.1.0 and later in all environments - Aura, IP Office and OpenSIP.
                        J129 SIP R1.0.0.0 (or R1.1.0.0), J100 SIP R2.0.0.0 and later, J139 SIP R3.0.0.0 and later;
                        Up to R2.0.0.0 (excluded) for IP office and 3PCC environments this parameter shall be set to 0 (As OPUS is supported in Avaya Aura environment only).
                        R2.0.0.0 and later supports OPUS in all environments.
                        Avaya Equinox 3.1.2 and later
                        SET ENABLE_OPUS 0"
                    ::= { endptApps 48 }
endptVLANSEPMODE OBJECT-TYPE
                    SYNTAX      INTEGER
                    MAX-ACCESS  read-only
                    STATUS      current
                    DESCRIPTION "Specifies whether full VLAN separation will be enabled by the built-in 
                        Ethernet switch while the telephone is tagging frames with a non-zero VLAN ID.
                        This varaible returns:
                        '0'    Disabled (default)
                        '1'    Enabled if VLANSEP, L2Q, L2QVLAN and PHY2VLAN are set appropriately
                        "
                    ::= { endptApps 49}
endptSHOWLASTEXTENSION OBJECT-TYPE
                    SYNTAX      INTEGER
                    MAX-ACCESS  read-only
                    STATUS      current
                    DESCRIPTION "Enables or disables Save Extension After Logout feature.
                        This varaible returns:
                        '0'    Disabled (default)
                        '1'    Enabled
                        "
                    ::= { endptApps 50}
endptGUESTLOGINSTAT   OBJECT-TYPE
                    SYNTAX      INTEGER
                    MAX-ACCESS  read-only
                    STATUS      current
                    DESCRIPTION "Enables or disables Guest Login Feature.
                    This varaible returns:
                        '0'    Disabled (default)
                        '1'    Enabled
                        "
                    ::= { endptApps 51 }
endptGUESTDURATION   OBJECT-TYPE
                    SYNTAX      INTEGER
                    MAX-ACCESS  read-only
                    STATUS      current
                    DESCRIPTION "Allows users to define duration for the guest session.
                    Number of hours for guest login duration. Can be selected by the user in
                    range 1-12 hours, with a default of 2"
                    ::= { endptApps 52 }
endptGUESTWARNING    OBJECT-TYPE
                    SYNTAX      INTEGER
                    MAX-ACCESS  read-only
                    STATUS      current
                    DESCRIPTION "Allows Admins to define time when warning screen is shown to the user prior
                    to session termination.
                    Range: 1-15, with a default of 5"
                    ::= { endptApps 53 }
endptGUESTLOGINACTIVE    OBJECT-TYPE
                    SYNTAX      INTEGER
                    MAX-ACCESS  read-only
                    STATUS      current
                    DESCRIPTION "Allows other features to query the current state of guest session.
                    This will primarily be used by 'Quick Login' feature to detect if the current
                    session is for a guest or for a regular user.
                    Range is 0-1, with a default of 0"
                    ::= { endptApps 54 }
endptCUSTOMIZATIONMAP    OBJECT-TYPE
                    SYNTAX      DisplayString
                    MAX-ACCESS  read-only
                    STATUS      current
                    DESCRIPTION "Stores information on customization (assigning favorites at specific
                    lines on phone and button modules) for favorites (features, autodials, contacts 
                    and applications) and call appearances."
                    ::= { endptApps 55 }
endptHEADSETType  OBJECT-TYPE
                    SYNTAX INTEGER
                    MAX-ACCESS    read-only
                    STATUS        current
                    DESCRIPTION   "Type of headset. 0 - Wired, 1 - Wireless, 2 - USB"
                    ::= { endptApps 56 }
endptHEADSETGainDefault  OBJECT-TYPE
                    SYNTAX INTEGER
                    MAX-ACCESS    read-only
                    STATUS        current
                    DESCRIPTION   "Index of hex array used for headset Tx gain adjustment:
                        0: 0x400;
                        1: 0x5aa;
                        2: 0x800;
                        3: 0xb4d;
                        4: 0x1000."
                    ::= { endptApps 57 }
endptPhoneKeyListSize OBJECT-TYPE
                    SYNTAX       INTEGER
                    MAX-ACCESS   read-only
                    STATUS       current
                    DESCRIPTION  "Number of pre-configured phone keys"
                    ::= { endptApps 58 }
endptPhoneKeyListTable OBJECT-TYPE
                    SYNTAX SEQUENCE OF EndptPhoneKeyListTableEntry
                    MAX-ACCESS   not-accessible
                    STATUS       current
                    DESCRIPTION  "List of pre-configured phone keys retrieved from settings file and
                    being stored in PHONE_KEY_LIST configuration parameter"
                    ::= { endptApps 59 }
endptPhoneKeyListTableEntry OBJECT-TYPE
                    SYNTAX EndptPhoneKeyListTableEntry
                    MAX-ACCESS   not-accessible
                    STATUS       current
                    DESCRIPTION  "Entry of the phone key list table (represents a phone key)"
                    INDEX { endptPhoneKeyListIndex }
                    ::= { endptPhoneKeyListTable 1 }
EndptPhoneKeyListTableEntry   ::=
                    SEQUENCE  {
                        endptPhoneKeyListIndex  INTEGER,
                        endptPhoneKeyLocation   INTEGER,
                        endptPhoneKeyType       DisplayString,
                        endptPhoneKeyName       DisplayString,
                        endptPhoneKeyAttr1      DisplayString,
                        endptPhoneKeyAttr2      DisplayString,
                        endptPhoneKeyLabel      DisplayString,
                        endptPhoneKeyForced     DisplayString
                    }
endptPhoneKeyListIndex OBJECT-TYPE
                    SYNTAX INTEGER
                    MAX-ACCESS not-accessible
                    STATUS current
                    DESCRIPTION "Phone key list index"
                    ::= { endptPhoneKeyListTableEntry 1 }
endptPhoneKeyLocation OBJECT-TYPE
                    SYNTAX INTEGER
                    MAX-ACCESS read-only
                    STATUS current
                    DESCRIPTION "Location (number of line) of the phone key on the screen"
                    ::= { endptPhoneKeyListTableEntry 2 }
endptPhoneKeyType   OBJECT-TYPE
                    SYNTAX DisplayString (SIZE(0..255))
                    MAX-ACCESS read-only
                    STATUS current
                    DESCRIPTION "Type of item represented by the phone key.
                    Possible values are 'feature', 'application', 'line' etc."
                    ::= { endptPhoneKeyListTableEntry 3 }
endptPhoneKeyName   OBJECT-TYPE
                    SYNTAX DisplayString (SIZE(0..255))
                    MAX-ACCESS read-only
                    STATUS current
                    DESCRIPTION "Name of the application/feature/line related to the phone key.
                    E.g. 'Logout' for Log out application, 'CFWD' for Call Forward feature..."
                    ::= { endptPhoneKeyListTableEntry 4 }
endptPhoneKeyAttr1  OBJECT-TYPE
                    SYNTAX DisplayString (SIZE(0..255))
                    MAX-ACCESS read-only
                    STATUS current
                    DESCRIPTION "Additional attribute 1 (optional)"
                    ::= { endptPhoneKeyListTableEntry 5 }
endptPhoneKeyAttr2  OBJECT-TYPE
                    SYNTAX DisplayString (SIZE(0..255))
                    MAX-ACCESS read-only
                    STATUS current
                    DESCRIPTION "Additional attribute 2 (optional)"
                    ::= { endptPhoneKeyListTableEntry 6 }
endptPhoneKeyLabel  OBJECT-TYPE
                    SYNTAX DisplayString (SIZE(0..255))
                    MAX-ACCESS read-only
                    STATUS current
                    DESCRIPTION "Label (identifier) of the phone key (optional)"
                    ::= { endptPhoneKeyListTableEntry 7 }
endptPhoneKeyForced OBJECT-TYPE
                    SYNTAX DisplayString (SIZE(0..255))
                    MAX-ACCESS read-only
                    STATUS current
                    DESCRIPTION "Is the phone key forced (can't be moved, deleted or renamed) (optional).
                    Possible values are 'true' and 'false'"
                    ::= { endptPhoneKeyListTableEntry 8 }
endptMPGROUPSTOLISTEN OBJECT-TYPE
                    SYNTAX DisplayString
                    MAX-ACCESS    read-only
                    STATUS        current
                    DESCRIPTION   "The Multicast Paging Groups to listen."
                    ::= { endptApps 60 }
endptMPGROUPSTOSEND OBJECT-TYPE
                    SYNTAX DisplayString
                    MAX-ACCESS    read-only
                    STATUS        current
                    DESCRIPTION   "The Multicast Paging Groups to send."
                    ::= { endptApps 61 }
endptMPCODEC OBJECT-TYPE
                    SYNTAX INTEGER
                    MAX-ACCESS    read-only
                    STATUS        current
                    DESCRIPTION   "The Multicast Paging codec currently in use. Range is 1-7, default is 1."
                    ::= { endptApps 62 }
endptMPPACKETSIZE OBJECT-TYPE
                    SYNTAX INTEGER
                    MAX-ACCESS    read-only
                    STATUS        current
                    DESCRIPTION   "The Multicast Paging packet size. Range is 10-80 milliseconds, default is 20.
                    Don't change it, unless necessary." 
                    ::= { endptApps 63 }
endptMPENABLED OBJECT-TYPE
                    SYNTAX INTEGER
                    MAX-ACCESS    read-only
                    STATUS        current
                    DESCRIPTION   "1 if the Multicast Paging feature is enabled and 0 otherwise, default is 0."
                    ::= { endptApps 64 }
endptMPCALLPRIORITY OBJECT-TYPE
                    SYNTAX INTEGER
                    MAX-ACCESS    read-only
                    STATUS        current
                    DESCRIPTION   "The Multicast Paging call priority. Range is 1-16, default is 3."
                    ::= { endptApps 65 }
endptAPPLICATIONHEADERAPPEARANCECONTEXT OBJECT-TYPE
                    SYNTAX INTEGER
                    MAX-ACCESS    read-only
                    STATUS        current
                    DESCRIPTION   "Specifies how the header line on phone screen displays contextual information regarding various states of the lines. 
                                   When idle the line can optionally display the users configured DISPLAY_NAME and SHORT_FORM_USER_ID.

                                   Disable (0) - no contextual information on the header line;
                                   Enable with extra context (1) - enables contextual information for various states, including name of the shared line key or BLF key, when applicable;
                                   Enable (2) - enables contextual information for various states, including name of BLF key, when applicable.

                                   Default: Disable"
                    ::= { endptApps 66 }
endptENABLEPARKDYNAMICANDPAGE OBJECT-TYPE
                    SYNTAX INTEGER
                    MAX-ACCESS    read-only
                    STATUS        current
                    DESCRIPTION   "Specifies whether the Park and Page feature is available to the user.
                                   The Park Dynamic and Page feature requires that the CALL_PARK_DYNAMIC_FAC code and
                                   CALL_PARK_DYNAMIC_METHOD are defined in order to park the call
                                   0 - Park Dynamic and Page feature is not available to the user(Default)
                                   1 - Park Dynamic and Page feature is available to the user"
                    ::= { endptApps 67 }
endptCALLPARKDYNAMICMETHOD OBJECT-TYPE
                    SYNTAX INTEGER
                    MAX-ACCESS    read-only
                    STATUS        current
                    DESCRIPTION   "CALL_PARK_DYNAMIC_METHOD specifies the method the phone will use to park an active call to a 
                                   dynamic parking slot assigned by the server.
                                   0 - Blind Transfer: The active call is blind transfered to the CALL_PARK_DYNAMIC_FAC (Default)
                                   1 - DTMF: Inject the CALL_PARK_DYNAMIC_FAC digits into the active call"
                    ::= { endptApps 68 }
endptCALLPARKDYNAMICFAC OBJECT-TYPE
                    SYNTAX DisplayString
                    MAX-ACCESS    read-only
                    STATUS        current
                    DESCRIPTION   "CALL_PARK_DYNAMIC_FAC specifies the Feature Access Code that the phone will use to park an
                                   active call to a dynamic parking slot assigned by the server.
                                   Default is '' (null)"
                    ::= { endptApps 69 }
endptCALLPAGEEXTENSIONFAC OBJECT-TYPE
                    SYNTAX DisplayString
                    MAX-ACCESS    read-only
                    STATUS        current
                    DESCRIPTION   "CALL_PAGE_EXTENSION_FAC specifies the Page feature access code that is used to inform the server to perform a page to an extension.
                                   Default is '' (null)"
                    ::= { endptApps 70 }
endptENABLEREDIALLIST OBJECT-TYPE
                    SYNTAX INTEGER
                    MAX-ACCESS    read-only
                    STATUS        current
                    DESCRIPTION   "Determines whether phone redials the last number or displays list of recently dialed numbers."
                    ::= { endptApps 71 }
endptSHORTCUTACTIONCONTACT OBJECT-TYPE
                    SYNTAX INTEGER
                    MAX-ACCESS    read-only
                    STATUS        current
                    DESCRIPTION   "Specifies the action which should be performed when Contact line is activated during an active call. 
                    For the 'Park' option please verify that the 'Call Park FAC' is defined correctly."
                    ::= { endptApps 72 } 
endptSHORTCUTACTIONAUTODIAL OBJECT-TYPE
                    SYNTAX INTEGER
                    MAX-ACCESS    read-only
                    STATUS        current
                    DESCRIPTION   "Specifies the action which should be performed when Autodial line is activated during an active call.
                    For the 'Park' option please verify that the 'Call Park FAC' is defined correctly."
                    ::= { endptApps 73 }                    
endptPHONELOCKPIN OBJECT-TYPE
                    SYNTAX DisplayString
                    MAX-ACCESS    read-only
                    STATUS        current
                    DESCRIPTION   "PIN to unlock the phone with"
                    ::= { endptApps 74 }                    
endptRTCPPUBLISHADDRESS OBJECT-TYPE
                    SYNTAX DisplayString
                    MAX-ACCESS    read-only
                    STATUS        current
                    DESCRIPTION   "Used in SIP URI target. Phone sends VQ-RTCPXR service quality metric reports using this address in SIP PUBLISH message to the 
                    central report collector. This parameter works independent of RTCP Monitoring settings. This address should not have sip scheme. 
                    A valid example: user@domain.com, an invalid example: sip:user@domain.com"
                    ::= { endptApps 75 }                    
endptCALLPAGINGGROUPS OBJECT-TYPE
                    SYNTAX DisplayString
                    MAX-ACCESS    read-only
                    STATUS        current
                    DESCRIPTION   "This parameter specifies a comma separated list of paging groups a user is allowed to call (PagingGroupLabel:PagingGroupAddress). 
                    PagingGroupLabel is a string describing the PagingGroupAddress. PagingGroupAddress is the address/number of the PagingGroupLabel."
                    ::= { endptApps 76 }
endptHOMEIDLETIME OBJECT-TYPE
                    SYNTAX INTEGER
                    MAX-ACCESS    read-only
                    STATUS        current
                    DESCRIPTION   "The phone activates the home view if it remains idle for the specified period of time (in minutes). Ranges from 0 to 30."
                    ::= { endptApps 77 }
endptCODECPRIORITY OBJECT-TYPE
                    SYNTAX DisplayString
                    MAX-ACCESS    read-only
                    STATUS        current
                    DESCRIPTION   "Defines the order of codecs in the SDP offer"
                    ::= { endptApps 78 }
endptEFFECTOFREDIALBUTTON OBJECT-TYPE
                    SYNTAX INTEGER
                    MAX-ACCESS    read-only
                    STATUS        current
                    DESCRIPTION   "Specifies whether to show a list, one number or option provided by Default redial list mode parameter on Redial Softkey.
                    Ranges from 0 to 2. 
                    1 by default."
                    ::= { endptApps 79 }
endptIGNOREBLFLINEKEY  OBJECT-TYPE
                    SYNTAX INTEGER
                    MAX-ACCESS    read-only
                    STATUS        current
                    DESCRIPTION   "Specifies if Softkey1 action will not be performed when the user presses line key associated with a BLF line, 
                    this parameter is not applicable when the user presses a BLF key in a Conference/Transfer/Page Target or similar selection modes.
                    This setting applies to 3PCC environment only.
					Range: 0-1
					Default: 0"
                    ::= { endptApps 80 }
endptANSWEREDELSEWHEREPOLICY OBJECT-TYPE
                    SYNTAX INTEGER
                    MAX-ACCESS    read-only
                    STATUS        current
                    DESCRIPTION   "This parameter defines the local call log behaviour when an incoming call to the phone is answered elsewhere by another user or device. 
                    The call log can show this call: as missed call or as answered call"
                    ::= { endptApps 81 }
endptPRIMARYLINEEXTENSION OBJECT-TYPE
                    SYNTAX DisplayString
                    MAX-ACCESS    read-only
                    STATUS        current
                    DESCRIPTION   "Specifies the default label for primary (shared and private) lines. It will be used if the label for a primary call appearance was not customized."
                    ::= { endptApps 82 }
endptDIRTOLOCALMAPPING OBJECT-TYPE
                    SYNTAX DisplayString
                    MAX-ACCESS    read-only
                    STATUS        current
                    DESCRIPTION   "Specifies a mapping of LDAP fields to local contact fields. The entire contact mapping is considered invalid if there is no a valid rule for either 
                    first name or last name or there is no a valid rule for at least one contact number. Local contact filelds names can be assigned from the following list: 
                    'lastName', 'firstName', 'nickname', 'URI', 'extension', 'email', 'department', 'zipCode', 'country'. For number types: 'work', 'home', 'mobile', 'other'.
                    Default value 'fn=firstName, ln=lastName, cn=nickname, telephoneNumber=work'"
                    ::= { endptApps 83 }
endptDIRLDAPDESCRIPTION OBJECT-TYPE
                    SYNTAX DisplayString
                    MAX-ACCESS    read-only
                    STATUS        current
                    DESCRIPTION   "Specifies a custom label to be used for the LDAP directory in the Contacts application. Default label is 'LDAP Directory' if this value is not specified."
                    ::= { endptApps 84 }
endptCALLPAGEGROUPFAC OBJECT-TYPE
                    SYNTAX DisplayString
                    MAX-ACCESS    read-only
                    STATUS        current
                    DESCRIPTION   "The Call Page Group FAC specifies the feature access code that phone will prepend to a user selected Paging Group call. 
                    If the Call Page Group FAC is not defined then a user selected Paging Group address will be dialed directly"
                    ::= { endptApps 85 }
endptPHONELOCKIDLETIMEUSER OBJECT-TYPE
                    SYNTAX INTEGER
                    MAX-ACCESS    read-only
                    STATUS        current
                    DESCRIPTION   "Indicates a period of time after which the phone becomes locked if remains idle. Can be set by a user. 
                    -1 (default) means the administrator value (PHONE_LOCK_IDLE_TIME) will be used"
                    ::= { endptApps 86 }
endptPHONELOCKPASSWORDFAILEDATTEMPTS OBJECT-TYPE
                    SYNTAX INTEGER
                    MAX-ACCESS    read-only
                    STATUS        current
                    DESCRIPTION   "The number of consecutive failed attempts to unlock that phone that are permitted. 
                    Once the maximum is reached, the user will be blocked from further attempts for a period of time before being allowed to attempt again. 
                    If set to 0 (default), the user will never be blocked from attempting to unlock the phone."
                    ::= { endptApps 87 }
endptPHONELOCKPASSWORDLOCKEDTIME OBJECT-TYPE
                    SYNTAX INTEGER
                    MAX-ACCESS    read-only
                    STATUS        current
                    DESCRIPTION   "The length of time that the user will be blocked from attempting to unlock the phone if the maximum number of failed unlock attempts is exceeded."
                    ::= { endptApps 88 }
endptIGNORELINEKEY OBJECT-TYPE
                    SYNTAX INTEGER
                    MAX-ACCESS    read-only
                    STATUS        current
                    DESCRIPTION   "Specifies if Softkey1 action will be performed when the users call appearance is on an active call and the user presses the 
                    line button associated with the active call appearance.
                    Ranges 0 - 1 (default)."
                    ::= { endptApps 89 }
endptSCROLLINGMODE OBJECT-TYPE
                    SYNTAX INTEGER
                    MAX-ACCESS    read-only
                    STATUS        current
                    DESCRIPTION   "Specifies the scrolling mode on the Phone and Features screens. 
                    Line scrolling - the phone can be navigated by Nav Up and Down keys so the previous/next line is selected, 
                    Left and Right Nav keys allow to select another column in dual screen mode. 
                    Page scrolling - by pressing Left and Right nav keys the phone will switch to the previous/next page.
                    Ranges 0 (default) - 1."
                    ::= { endptApps 90 }
endptCALLFORWARDDELAYUSER OBJECT-TYPE
                    SYNTAX INTEGER
                    MAX-ACCESS    read-only
                    STATUS        current
                    DESCRIPTION   "Specifies the number of rings after which a call will be forwarded if it remains unanswered.
                    Ranges 0 (default)- 20. 
                    0 means the value of the CALL_FORWARD_DELAY will be used."
                    ::= { endptApps 91 }
endptKEYUSAGEREQUIRED OBJECT-TYPE
                    SYNTAX INTEGER
                    MAX-ACCESS    read-only
                    STATUS        current
                    DESCRIPTION   "Enable or disable checking the server certificate for the presence of a Key Usage extension. 
                    If enabled, a server certificate will be rejected if the Key Usage extension is missing.
                    Ranges 0 (default) - 1."
                    ::= { endptApps 92 }
endptLANGUAGES OBJECT-TYPE
                    SYNTAX DisplayString
                    MAX-ACCESS    read-only
                    STATUS        current
                    DESCRIPTION   "Remove download limitation of only 4 Mlf_*.xml language files and limitation of 1096 ascii characters of filenames."
                    ::= { endptApps 93 }
endptSHOWCALLFORONPRIMARY OBJECT-TYPE
                    SYNTAX INTEGER
                    MAX-ACCESS    read-only
                    STATUS        current
                    DESCRIPTION   "Specifies whether to 'Incoming call' pop-ups displayed with 'Call for' when call to primary private or shared line only:
                    0 - don't display 'Call for' for primary private or shared line only
                    1 - display 'Call for' for primary private or shared line only"
                    ::= { endptApps 94 }
endptREDIALLISTMODEDEFAULT OBJECT-TYPE
                    SYNTAX INTEGER
                    MAX-ACCESS    read-only
                    STATUS        current
                    DESCRIPTION   "If this parameter is set to 'Last number redial' or 'Redial list', then it specifies default 'Redial' button action. 
                    If this parameter is set to forced, then the 'Redial Softkey Options' parameter will be ignored and the option to pick effect of 
                    redial button disappears from Phone UI user menu.
                    Ranges 0 (default) - 3."
                    ::= { endptApps 95 }
endptPHNDAC OBJECT-TYPE
                    SYNTAX DisplayString
                    MAX-ACCESS    read-only
                    STATUS        current
                    DESCRIPTION   "Dial access code - will be applied if the dialed number length + the length of the Dial access code length equals the national number length. 
                    This calculation does not include an outside line access code. 
                    It is different from PHNLAC since PHNLAC is applied when the phone number length is more than ext number length and less than national number length."
                    ::= { endptApps 96 }
endptDOWNLOADABLEDIRECTORY OBJECT-TYPE
                    SYNTAX DisplayString
                    MAX-ACCESS    read-only
                    STATUS        current
                    DESCRIPTION   "This parameter specifies the name of the downloadable directory file (XML) that has directory contacts. 
                    This file is expected to be present at the same location where 46xxsettings.txt is available on the file server. 
                    This feature is applicable to all environment excluding the IPO SIP and IPO CCMS."
                    ::= { endptApps 97 }
endptDIALINGMODEDEFAULT OBJECT-TYPE
                    SYNTAX INTEGER
                    MAX-ACCESS    read-only
                    STATUS        current
                    DESCRIPTION   "If this parameter is set to 'Automatic' or 'Manual', then it specifies default dialing mode. 
                    If this parameter is set to forced, then the option to pick dialing mode disappears from Phone UI user menu.
                    Ranges 0 - 3.
                    1 is default."
                    ::= { endptApps 98 }

endptENABLEWMLPUSHALERTING OBJECT-TYPE
                    SYNTAX INTEGER
                    MAX-ACCESS    read-only
                    STATUS        current
                    DESCRIPTION   "Specifies the behavior of WML browser during incoming call.
                    Values
                    0 - (Default) WML bowser disappears when the phone starts ringing and an incoming call appears instead.
                    1 - WML browser still appears when the phone starts ringing and user can answer a call by off-hook from WML browser application."
                    ::= { endptApps 99 }

endptRTCPXR OBJECT-TYPE
                    SYNTAX INTEGER
                    MAX-ACCESS    read-only
                    STATUS        current
                    DESCRIPTION   "Specifies whether and how VoIP Metrics Report Block as defined in RTP Control Protocol Extended Reports (RTCP XR) (RFC 3611) is sent.
                    0 (Default) - No Extended Report (RTCP XR) is sent
                    1 - Extended Report (RTCP XR) is sent to voice monitoring servers (if configured) as well as to the remote peer
                    2 - Extended Report (RTCP XR) is sent to voice monitoring servers (if configured) but not to the remote peer."
                    ::= { endptApps 100 }

endptREJECTPAGEDURINGCALL OBJECT-TYPE
                    SYNTAX INTEGER
                    MAX-ACCESS    read-only
                    STATUS        current
                    DESCRIPTION   "Defines the behaviour of a page target device when there is already an active call session on the device.
                    This parameter will only be followed when the J100 is deployed in a RingCentral or Avaya Cloud Office environment when receiving a SIP INVITE with header p-rc-api-call-info: callAttributes=paging-call
                    When this parameter is enabled, it has priority over AUTO_ANSWER_DURING_CALL
                    0 (Default) Do not reject the page
                    1 Reject the page with SIP 486 Busy here"
                    ::= { endptApps 101 }

endptRESTURL OBJECT-TYPE
             SYNTAX      DisplayString
             MAX-ACCESS  read-only
             STATUS      current
             DESCRIPTION "Specifies server URL to REST service. 
                          REST URL parameter is supported with 3PPC Environments Ring Central and Avaya Cloud Office only.
                          REST URL parameter value should follow common URL syntax, example: https://example.com:443/..."
             ::= { endptApps 102 }

endptENABLEDIGITMAPPING  OBJECT-TYPE
                SYNTAX      INTEGER
                MAX-ACCESS  read-only
                STATUS      current
                DESCRIPTION "Specifies if DIGIT_MAPPING config parameter will be used for dial plan configuration, if the parameter is disabled DIALPLAN and ELD config parameters will be used.
                '0' Disable (Default) - DIALPLAN and ELD rules will be applied to the dial number.
                '1' Enable - DIGIT_MAPPING rules will be applied to the dial number.
                Is not applied in Avaya and CCMS"
                ::= { endptApps 103 }

endptDIGITMAPPING OBJECT-TYPE
             SYNTAX      DisplayString
             MAX-ACCESS  read-only
             STATUS      current
             DESCRIPTION "Specifies a digit map which can be used to match digits to ensure a complete number is dialed, transform dialed digits, and block numbers from being dialed. ',' is used for rules saparation. The following elements can be used to configure the rules:
            Literals - matches digit sequences with exactly the same literals.
            x - wildcard matches any character
            . Matching Function - matches 0 or more of the previous element
            [ ] Set - enclose a set of numerals and/or characters that are used to match a single digit or character.
            [^ ] Exclusion Set - An exclusion set matches any single alphanumeric character that is not within the set.
            ! Call Bar - To bar users from calling numbers that match a rule, add an exclamation mark - ! - in front of that rule in the digit map.
            < elements : literals > - Element to Literal Transformation allows replacing of characters sequence matching elements with the given literals. Use this rule to remove digits from a dialed number, add digits to a dialed number, or transform a dialed number
            Is not applied in Avaya and CCMS"
             ::= { endptApps 104 }

endptAdjuncts   OBJECT IDENTIFIER ::= { avayaSparkMIB 5 }
endptBMODS      OBJECT-TYPE
                    SYNTAX      INTEGER
                    MAX-ACCESS  read-only
                    STATUS      current
                    DESCRIPTION "Button Modules attached. This variable returns
                        the number of Button Modules attached (or daisy-chained)
                        to the endpoint."
                    ::= { endptAdjuncts 1}
endptBM1HWVER  OBJECT-TYPE
                    SYNTAX      DisplayString 
                    MAX-ACCESS  read-only
                    STATUS      current
                    DESCRIPTION "Button Module hardware version. This variable returns the 
                        hardware version of the first button module attached, if any.  
                        If none, null is returned."
                    ::= {endptAdjuncts 2}
endptBM1SWVER  OBJECT-TYPE
                    SYNTAX      DisplayString 
                    MAX-ACCESS  read-only
                    STATUS      current
                    DESCRIPTION "Button Module software version. This variable returns the 
                        software version of the first button module attached, if any.  
                        If none, null is returned."
                    ::= {endptAdjuncts 3}
endptBM2HWVER  OBJECT-TYPE
                    SYNTAX      DisplayString
                    MAX-ACCESS  read-only
                    STATUS      current
                    DESCRIPTION "Button Module hardware version. This variable returns the 
                        hardware version of the second button module attached, if any.  
                        If none, null is returned."
                    ::= { endptAdjuncts 4}
endptBM2SWVER  OBJECT-TYPE
                    SYNTAX      DisplayString 
                    MAX-ACCESS  read-only
                    STATUS      current
                    DESCRIPTION "Button Module software version. This variable returns the 
                        software version of the second button module attached, if any.  
                        If none, null is returned."
                    ::= {endptAdjuncts 5}
endptBM3HWVER  OBJECT-TYPE
                    SYNTAX      DisplayString 
                    MAX-ACCESS  read-only
                    STATUS      current
                    DESCRIPTION "Button Module hardware version. This variable returns the 
                        hardware version of the third button module attached, if any.  
                        If none, null is returned."
                    ::= {endptAdjuncts 6}
endptBM3SWVER  OBJECT-TYPE
                    SYNTAX      DisplayString 
                    MAX-ACCESS  read-only
                    STATUS      current
                    DESCRIPTION "Button Module software version. This variable returns the 
                        software version of the third button module attached, if any.  
                        If none, null is returned."
                    ::= {endptAdjuncts 7}

endptSIP   OBJECT IDENTIFIER ::= { avayaSparkMIB 7 }
endptALPHANUMDIALING  OBJECT-TYPE                   
                    SYNTAX      INTEGER                   
                    MAX-ACCESS  read-only
                    STATUS      current
                    DESCRIPTION "Alphanumeric dialing mode. This variable 
                        returns 0 if only numeric dialing is possible, else 1."
                    ::= { endptSIP 1 }
endptAVAYAENVIRONMENT  OBJECT-TYPE
                    SYNTAX      INTEGER
                    MAX-ACCESS  read-only
                    STATUS      current
                    DESCRIPTION "Avaya environment mode. This variable returns 
                        0 if the endpoint is supposed to operate in a 3rd-party
                        SIP proxy environment, and 1 if it suppossed to operate
                        in an Avaya SES/CM environment."
                    ::= { endptSIP 2 }
endptCONFSRVR   OBJECT-TYPE
                    SYNTAX      DisplayString
                    MAX-ACCESS  read-only
                    STATUS      current
                    DESCRIPTION "Conference server URI. This variable is 
                        a placeholder for future use."
                    ::= { endptSIP 3 }
endptCONFSRVRINUSE  OBJECT-TYPE
                    SYNTAX      IpAddress
                    MAX-ACCESS  read-only
                    STATUS      current
                    DESCRIPTION "Conference server IP address.  This variable  
            returns a 4-octet IP address for the server used for 
                        server-based conferencing (all zeros if no conference 
                        server used)."
                    ::= { endptSIP 4 }
endptCONFTYPE   OBJECT-TYPE
                    SYNTAX      INTEGER
                    MAX-ACCESS  read-only
                    STATUS      current
                    DESCRIPTION "Conference Type. This variable returns 0 if 
                        the endpoint supports local conferencing, 1 if it  
                        supports SIP-AST server-based conferencing, and 2 if  
                        it supports 'click-to-conference'-based conferencing."
                    ::= { endptSIP 5 }
endptDIALPLAN   OBJECT-TYPE
                    SYNTAX      DisplayString
                    MAX-ACCESS  read-only
                    STATUS      current
                    DESCRIPTION "SIP dial plan.  This variable returns the 
                        administered dial plan, used during manual dialing to                 
                        allow a call to be initiated without the use of a Send  
                        button and without waiting for the expiration of a 
                        timeout interval; up to 1000 characters; not used in 
                        an Avaya SES SIP proxy environment."
                    ::= { endptSIP 6 }
endptEARLYMEDIA  OBJECT-TYPE
                    SYNTAX      INTEGER
                    MAX-ACCESS  read-only
                    STATUS      current
                    DESCRIPTION "Early media mode. This variable returns 0 if 
                        SIP early media is off/disabled, else 1."
                    ::= { endptSIP 7 }
endptMUSICSRVR  OBJECT-TYPE
                    SYNTAX      DisplayString
                    MAX-ACCESS  read-only
                    STATUS      current
                    DESCRIPTION "Music server addresses. This variable returns 
                        zero or more IP addresses, in dotted decimal or DNS  
                        format and separated by commas, of Music-on-Hold 
                        servers available for use."
                    ::= { endptSIP 8 }
endptMUSICSRVRINUSE  OBJECT-TYPE
                    SYNTAX      IpAddress
                    MAX-ACCESS  read-only
                    STATUS      current
                    DESCRIPTION "Music server IP address. This variable returns 
            a 4-octet IP address for the Music-on-Hold server most 
            recently used (all zeros if no music server used)."
                    ::= { endptSIP 9 }
endptMWISRVR    OBJECT-TYPE
                    SYNTAX      DisplayString
                    MAX-ACCESS  read-only
                    STATUS      current
                    DESCRIPTION "Message Waiting Indication server addresses. 
                        This variable returns zero or more IP addresses, in 
                        dotted decimal or DNS format and separated by commas, of
                        Message Waiting Indication servers available for use."
                    ::= { endptSIP 10 }
endptMWISRVRINUSE  OBJECT-TYPE
                    SYNTAX      IpAddress
                    MAX-ACCESS  read-only
                    STATUS      current
                    DESCRIPTION "Message Waiting Indication server IP address. 
                        This variable returns a 4-octet IP address for the 
                        Message Waiting Indication servers most recently used 
                        (all zeros if no MWI server used)."
                    ::= { endptSIP 11 }
endptPHNNUMOFSA  OBJECT-TYPE
                    SYNTAX      INTEGER
                    MAX-ACCESS  read-only
                    STATUS      current
                    DESCRIPTION "Number of primary session appearances. This 
                        varaible returns the number of primary session 
                        appearances administered for the SIP endpoint."
                    ::= { endptSIP 12 }
endptPRESENCESRVR OBJECT-TYPE
                    SYNTAX      DisplayString
                    MAX-ACCESS  read-only
                    STATUS      current
                    DESCRIPTION "Presence server addresses. This variable 
                        returns zero or more IP addresses, in dotted decimal 
                        or DNS format and separated by commas, of presence 
                        servers available for use."
                    ::= { endptSIP 13 }
endptPRESENCESRVRINUSE OBJECT-TYPE
                    SYNTAX      DisplayString
                    MAX-ACCESS  read-only
                    STATUS      current
                    DESCRIPTION "Presence server IP address. This variable 
                        returns an IP address of the presence server most recently used."
                    ::= { endptSIP 14 }
endptPRESENCETYPE  OBJECT-TYPE
                    SYNTAX      INTEGER
                    MAX-ACCESS  read-only
                    STATUS      current
                    DESCRIPTION "Presence mode. This variable returns 0 if 
                        individual presence subscriptions are done separately, 
                        and 1 if subscription to (server-based) presence list 
                        and watcher info is performed."
                    ::= { endptSIP 15 }
endptREGISTERWAIT  OBJECT-TYPE
                    SYNTAX      Integer32
                    MAX-ACCESS  read-only
                    STATUS      current
                    DESCRIPTION "Registration wait interval. This variable 
                        returns the number of seconds between attempts to 
                        re-register with the current to SIP server."
                    ::= { endptSIP 16 }
endptSIPDOMAIN  OBJECT-TYPE
                    SYNTAX      DisplayString
                    MAX-ACCESS  read-only
                    STATUS      current
                    DESCRIPTION "SIP registration domain name. This variable 
                        returns the text used in the contact header field as 
                        part of SIP registration."
                    ::= { endptSIP 17 }
endptSIPMODE    OBJECT-TYPE
                    SYNTAX      INTEGER
                    MAX-ACCESS  read-only
                    STATUS      current
                    DESCRIPTION "SIP mode. This variable returns 0 if the 
                        endpoint operates in proxy mode, and 1 if it operates 
                        in peer-to-peer mode."
                    ::= { endptSIP 18 }
endptSIPPORT    OBJECT-TYPE
                    SYNTAX      INTEGER
                    MAX-ACCESS  read-only
                    STATUS      current
                    DESCRIPTION "TCP/UDP port used for SIP messages.  This 
                        variable returns the current port number used for SIP 
                        messaging via TCP or UDP. The default is 5060."
                    ::= { endptSIP 19 }
endptSIPPORTSECURE  OBJECT-TYPE
                    SYNTAX      INTEGER
                    MAX-ACCESS  read-only
                    STATUS      current
                    DESCRIPTION "TCP port used for SIP messages via secure link.
                        This variable returns the current port number used for 
                        SIP messaging via TLS over TCP. The default is 5061."
                    ::= { endptSIP 20 }
endptSIPSIGNAL  OBJECT-TYPE
                    SYNTAX      INTEGER
                    MAX-ACCESS  read-only
                    STATUS      obsolete
                    DESCRIPTION "SIP transport protocol. This variable returns
                        an integer specifying the transport protocol for  
                        SIP messaging: 0 for UDP, 1 for TCP, and 2 for 
                        TLS over TCP."
                    ::= { endptSIP 21 }
endptSIPPROXYSRVR  OBJECT-TYPE
                    SYNTAX      DisplayString
                    MAX-ACCESS  read-only
                    STATUS      current
                    DESCRIPTION "SIP proxy server addresses. This variable 
                        returns zero or one IP addresses, in dotted decimal or 
                        DNS format and separated by commas, of SIP proxy servers 
                        available for use."
                    ::= { endptSIP 22 }
endptSIPPROXYSRVRINUSE  OBJECT-TYPE
                    SYNTAX      DisplayString
                    MAX-ACCESS  read-only
                    STATUS      current
                    DESCRIPTION "SIP proxy server IP address. This variable 
                        returns an IP address of the SIP proxy server most recently used."
                    ::= { endptSIP 23 }
endptSIPREGISTRAR  OBJECT-TYPE
                    SYNTAX      DisplayString
                    MAX-ACCESS  read-only
                    STATUS      current
                    DESCRIPTION "SIP registrar addresses. This variable 
                        returns zero or more IP addresses, in dotted decimal or 
                        DNS format and separated by commas, of SIP registrars 
                        available for use."
                    ::= { endptSIP 24 }
endptSIPREGISTRARINUSE  OBJECT-TYPE
                    SYNTAX      IpAddress
                    MAX-ACCESS  read-only
                    STATUS      current
                    DESCRIPTION "SIP registrar IP address. This variable 
            returns a 4-octet IP address of the SIP registrar 
                        most recently used (all zeros if no SIP registrar 
                        used)."
                    ::= { endptSIP 25 }
endptSIPUSERACCOUNT  OBJECT-TYPE
                    SYNTAX      DisplayString
                    MAX-ACCESS  read-only
                    STATUS      current
                    DESCRIPTION "SIP user account. This variable returns the 
                        numeric or alphanumeric user name used for SIP 
                        registration."
                    ::= { endptSIP 26 }
endptSIPUSERID  OBJECT-TYPE
                    SYNTAX      DisplayString
                    MAX-ACCESS  read-only
                    STATUS      current
                    DESCRIPTION "SIP user ID. This variable returns the SIP 
                        user ID used in the authorization header field in case 
                        of re-issuing a registration request due to an 
                        authorization challenge from SIP proxy or SIP registrar
                        (if empty, the SIP user account is used in  
                        authorization header field)."
                    ::= { endptSIP 27 }
endptSIPUSERIDENABLED  OBJECT-TYPE
                    SYNTAX      INTEGER
                    MAX-ACCESS  read-only
                    STATUS      current
                    DESCRIPTION "SIP User ID mode. This variable returns 1 
                        if user is prompted for SIP user ID, else 0."
                    ::= { endptSIP 28 }
endptSNTPSRVR OBJECT-TYPE
                    SYNTAX      DisplayString
                    MAX-ACCESS  read-only
                    STATUS      current
                    DESCRIPTION "SNTP server addresses. This variable returns  
            zero or more IP addresses, in dotted decimal or DNS 
                        format and separated by commas, of SNTP time servers 
                        available for use."
                    ::= { endptSIP 29 }
endptSNTPSRVRUSED  OBJECT-TYPE
                    SYNTAX      DisplayString
                    MAX-ACCESS  read-only
                    STATUS      current
                    DESCRIPTION "SNTP server IP address. This variable returns
                        an IP address of the SNTP time server most recently used."
                    ::= { endptSIP 30 }
endptCALLFWDADDR  OBJECT-TYPE
                    SYNTAX      DisplayString
                    MAX-ACCESS  read-only
                    STATUS      current
                    DESCRIPTION "Call Forwarding address. This variable returns
                        the URI to which calls are forwarded; up to 255 
                        characters; not used in an Avaya SES SIP proxy 
                        environment."
                    ::= { endptSIP 31 }
endptCALLFWDDELAY  OBJECT-TYPE
                    SYNTAX      INTEGER
                    MAX-ACCESS  read-only
                    STATUS      current
                    DESCRIPTION "Call Forwarding delay. This variable returns 
                        the number of times the telephone will ring before a 
                        call is forwarded, if Call Forwarding on No Answer is 
                        selected; not used in an Avaya SES SIP proxy 
                        environment."
                    ::= { endptSIP 32 }
endptCALLFWDSTAT  OBJECT-TYPE
                    SYNTAX      INTEGER
                    MAX-ACCESS  read-only
                    STATUS      current
                    DESCRIPTION "Call Forwarding setting. This variable returns
                        the sum of all Call Forwarding permissions.  Range is 0
                        to 7, with 0 as the default. Not used in an Avaya SES SIP 
                        proxy environment."
                    ::= { endptSIP 33 }
endptCOVERAGEADDR  OBJECT-TYPE
                    SYNTAX      DisplayString
                    MAX-ACCESS  read-only
                    STATUS      current
                    DESCRIPTION "Call Coverage Server address. This variable 
                        returns the URI to which call coverage is sent; up to 
                        255 character; not used in an Avaya SES SIP proxy 
                        environment."
                    ::= { endptSIP 34 }
endptVUMODE       OBJECT-TYPE
                    SYNTAX      INTEGER
                    MAX-ACCESS  read-only
                    STATUS      current
                    DESCRIPTION "Visiting User mode. This variable returns 0 
                        if the endpoint only allows registrations as 'normal'  
                        user, 1 if the endpoint prompts the user at registration
                        time, whether or not they like to register as 'Visiting 
                        User', and 2 if the phone only allows registrations as 
                        'Visiting User'. The default is 0."
                    ::= { endptSIP 35 }
endptVUTIMER      OBJECT-TYPE
                    SYNTAX      INTEGER
                    MAX-ACCESS  read-only
                    STATUS      current
                    DESCRIPTION "Visiting User Timer. This variable returns
                        the idle time in seconds before the endpoint
                        queries a user registered as 'Visiting User' 
                        for re-registration."
                    ::= { endptSIP 36 }
endptSIPCONFERENCECONTINUE      OBJECT-TYPE
                    SYNTAX      INTEGER
                    MAX-ACCESS  read-only
                    STATUS      current
                    DESCRIPTION "Conference Continuation on host hangup mode.
                        When the AVAYAENVIRONMENT variable is 0, this parameter, 
                        this variable returns 0 when all conference parties are 
                        dropped when the conference host drops the conference 
                        and 1 when the conference continues when the conference 
                        host drops the conference."
                    ::= { endptSIP 37 }
endptSUBSCRIBESECURITY      OBJECT-TYPE
                    SYNTAX      INTEGER
                    MAX-ACCESS  read-only
                    STATUS      current
                    DESCRIPTION "Controls the use of SIP and SIPS subscriptions.
                        The variable returns 0 when the phone uses SIP for both 
                        the Request URI and the Contact Header regardless of 
                        whether SRTP is enabled.
                        The variable returns 1 when the phone uses SIPS for 
                        both the Request URI and the Contact Header 
                        if SRTP is enabled.
                        The variable returns 2 when the phone uses SIP for both 
                        the Request URI and the Contact Header in a 
                        SES/PPM 4.0 system, or when  the phone uses SIPS for both 
                        the Request URI and the Contact Header if SRTP is enabled."
                    ::= { endptSIP 38 }
endptFASTRESPONSETIMEOUT      OBJECT-TYPE
                    SYNTAX      INTEGER
                    MAX-ACCESS  read-only
                    STATUS      current
                    DESCRIPTION "Fast Response Timer. This variable returns the
                        value of the Fast Response Timer, in seconds."
                    ::= { endptSIP 39 }
endptRECOVERYREGISTERWAIT      OBJECT-TYPE
                    SYNTAX      INTEGER
                    MAX-ACCESS  read-only
                    STATUS      current
                    DESCRIPTION "Reactive Monitoring Interval. This variable returns 
                        the value of the Reactive Monitoring Interval, in seconds.
                        The default value is 60 seconds. The range is 10 to 36,000 seconds."
                    ::= { endptSIP 40 }
endptFAILBACKPOLICY      OBJECT-TYPE
                    SYNTAX      DisplayString
                    MAX-ACCESS  read-only
                    STATUS      current
                    DESCRIPTION "A policy to control how the phone fails back to 
                        the primary controller (proxy). 
                        This variable returns the value of either admin or auto."
                    ::= { endptSIP 41 }
endptSIPREGPROXYPOLICY      OBJECT-TYPE
                    SYNTAX      DisplayString
                    MAX-ACCESS  read-only
                    STATUS      current
                    DESCRIPTION "A policy to control how the phone treats a list of 
                        proxies in the SIP_CONTROLLER_LIST parameter.
                        This variable returns a value of either alternate or simultaneous."
                    ::= { endptSIP 42 }
endptPSTNVMNUM      OBJECT-TYPE
                    SYNTAX      DisplayString
                    MAX-ACCESS  read-only
                    STATUS      current
                    DESCRIPTION "The string that is dialed when the user presses
                        the Message button when the phone is not active on the
                        primary controller (proxy)"
                    ::= { endptSIP 43 }
endptDISCOVERAVAYAENVIRONMENT      OBJECT-TYPE
                    SYNTAX      INTEGER
                    MAX-ACCESS  read-only
                    STATUS      current
                    DESCRIPTION "Allows the phone to discover if the active controller
                        supports Avaya SIP AST features. The variable returns 0
                        if the phone does not discover the feature support. It
                        returns 1 (default) if the phone discovers feature support."
                    ::= { endptSIP 44 }
endptSYMMETRICRTP   OBJECT-TYPE
                    SYNTAX      INTEGER
                    MAX-ACCESS  read-only
                    STATUS      current
                    DESCRIPTION "Enforce RTP on the same port. The variable returns
                        1 if a UDP Source Port is forced to equal to the value of 
                        the far end port.  It returns 0 if the UDP Source Port is not checked."
                    ::= { endptSIP 45 }
endptEXTENDRINGTONE      OBJECT-TYPE
                    SYNTAX      DisplayString
                    MAX-ACCESS  read-only
                    STATUS      current
                    DESCRIPTION "The string represents a list of xml files 
                        that each represent custom ring tone information."
                    ::= { endptSIP 46 }
endptENABLEPPMSOURCEDSIPPROXYSRVR   OBJECT-TYPE
                    SYNTAX      INTEGER
                    MAX-ACCESS  read-only
                    STATUS      current
                    DESCRIPTION "Enables PPM as a source of SIP proxy server information.
                        The variable returns 1 if PPM is enabled as a source of SIP proxy server information.
                        The variable returns 0 if PPM is disabled as a source of SIP proxy server information."
                    ::= { endptSIP 47 }
endptINGRESSDTMFVOLLEVEL   OBJECT-TYPE
                    SYNTAX      INTEGER
                    MAX-ACCESS  read-only
                    STATUS      current
                    DESCRIPTION "RFC 2833 Digit event volume level. The power level of the tone, 
                        expressed in dBm0 after dropping the sign. (from RFC 2833 section 3.5 Payload Format)."
                    ::= { endptSIP 48 }
endptCONFTRANSONPRIMARYAPPR   OBJECT-TYPE
                    SYNTAX      INTEGER
                    MAX-ACCESS  read-only
                    STATUS      current
                    DESCRIPTION "Conference Transfer on Primary Appearance.
                        The variable returns 1 if active.  The variable returns 0 if inactive."
                    ::= { endptSIP 49 }
endptAUTOSELECTANYIDLEAPPR   OBJECT-TYPE
                    SYNTAX      INTEGER
                    MAX-ACCESS  read-only
                    STATUS      current
                    DESCRIPTION "Auto Select any Idle Appearance.
                        The variable returns 1 if active.  The variable returns 0 if inactive."
                    ::= { endptSIP 50 }
endptSIPCONTROLLERLIST      OBJECT-TYPE
                    SYNTAX      DisplayString
                    MAX-ACCESS  read-only
                    STATUS      current
                    DESCRIPTION "SIP proxy server addresses. This variable returns zero or 
                        more IP addresses, in dotted decimal, hex or DNS format and separated by commas, 
                        of SIP proxy servers available for use in priority order. 
                        The variable includes controllers entered through the Craft menu, 
                        those delivered by PPM and those included in the SIP_CONTROLLER_LIST or SIP_CONTROLLER_LIST2 parameters."
                    ::= { endptSIP 51 }
endptENABLEREMOVEPSTNACCESSPREFIX   OBJECT-TYPE
                    SYNTAX      INTEGER
                    MAX-ACCESS  read-only
                    STATUS      current
                    DESCRIPTION "Enables the removal of the PSTN access prefix.
                        When the phone is operating with a non-AST controller and the value of the 
                        parameter is 0, the PSTN access prefix, defined by the parameter PHNOL, 
                        is retained in the outgoing number. If the value is 1, then the PSTN 
                        access prefix is stripped from the outgoing number."
                    ::= { endptSIP 52 }
endptLOCALDIALAREACODE   OBJECT-TYPE
                    SYNTAX      INTEGER
                    MAX-ACCESS  read-only
                    STATUS      current
                    DESCRIPTION "A flag indicating whether the user must dial area code for 
                        calls within same area code. When the parameter is 0, the user does not 
                        need to dial area code; when 1, the user needs to dial area code."
                    ::= { endptSIP 53 }
endptPHNLAC         OBJECT-TYPE
                    SYNTAX      DisplayString
                    MAX-ACCESS  read-only
                    STATUS      current
                    DESCRIPTION " A string representing the phone's local area code."
                    ::= { endptSIP 54 }
endptCONTROLLERSEARCHINTERVAL   OBJECT-TYPE
                    SYNTAX      INTEGER
                    MAX-ACCESS  read-only
                    STATUS      current
                    DESCRIPTION "The controller search interval. The variable returns the
                        time in seconds that the phone waits to complete the maintenance check 
                        for monitored controllers. The default is 4 seconds. The range is 4 to 3600 seconds."
                    ::= { endptSIP 55 }
endptRDSINITIALRETRYATTEMPTS   OBJECT-TYPE
                    SYNTAX      INTEGER
                    MAX-ACCESS  read-only
                    STATUS      current
                    DESCRIPTION "Remote Data Source initial retry attempts. The variable returns the
                        number of times the phone tries to download from PPM.
                        The default is 15. The range is 1 to 30."
                    ::= { endptSIP 56 }
endptRDSINITIALRETRYTIME   OBJECT-TYPE
                    SYNTAX      INTEGER
                    MAX-ACCESS  read-only
                    STATUS      current
                    DESCRIPTION "Remote Data Source initial retry time. The variable returns the
                        initial delay, in seconds, for a retry attempt to PPM.
                        The default is 2. The range is 2 to 60 seconds."
                    ::= { endptSIP 57 }
endptRDSMAXRETRYTIME   OBJECT-TYPE
                    SYNTAX      INTEGER
                    MAX-ACCESS  read-only
                    STATUS      current
                    DESCRIPTION "Remote Data Source maximum retry time. The variable returns the
                        maximum delay interval before abandoning attempts to download from PPM.
                        The default is 600 seconds. The range is 2 to 3600 seconds."
                    ::= { endptSIP 58 }
endptPROXYSERVICEVERSION         OBJECT-TYPE
                    SYNTAX      DisplayString
                    MAX-ACCESS  read-only
                    STATUS      current
                    DESCRIPTION "The contents of the ServiceVersion string from PPM."
                    ::= { endptSIP 59 }
endptPRIMARYPROXYENVIRONMENT   OBJECT-TYPE
                    SYNTAX      INTEGER
                    MAX-ACCESS  read-only
                    STATUS      current
                    DESCRIPTION "The type of primary proxy. The variable returns a
                        0 for a non-AST (3rd party) controller, a 1 for SES, and a
                        2 for Avaya Aura(tm) Session Manager."
                    ::= { endptSIP 60 }
endptPHNMUTEALERTBLOCK   OBJECT-TYPE
                    SYNTAX      INTEGER
                    MAX-ACCESS  read-only
                    STATUS      current
                    DESCRIPTION "Blocks the  Mute Alert feature. The variable returns a
                        1 (default) when the feature is blocked and a 0 when
                        the feature is unblocked."
                    ::= { endptSIP 61 }
endptENFORCESIPSURI   OBJECT-TYPE
                    SYNTAX      INTEGER
                    MAX-ACCESS  read-only
                    STATUS      current
                    DESCRIPTION "Controls the enforcement of SIPS URI with SRTP. The variable returns a
                        1 (default) when the phone accepts and uses only SIPS URI for incoming and 
                        outgoing calls with SRTP media encryption. It returns a 0 when the phone allows 
                        either SIP URI or SIPS URI for incoming SRTP media encryption calls and uses 
                        only SIP URI for outgoing SRTP media encryption calls."
                    ::= { endptSIP 62 }
endptMSGNUM         OBJECT-TYPE
                    SYNTAX      DisplayString
                    MAX-ACCESS  read-only
                    STATUS      current
                    DESCRIPTION "The dialable number used to call the messaging system when 
                        the user presses the Message button."
                    ::= { endptSIP 63 }
endptREDIRECTTONE   OBJECT-TYPE
                    SYNTAX      INTEGER
                    MAX-ACCESS  read-only
                    STATUS      current
                    DESCRIPTION "Redirect (call coverage) tone. The variable returns a
                        1 (default) when the first call coverage tone is provisioned. It
                        returns a 2 when the second tone is provisioned, 3 when the third tone
                        is provisioned and 4 when the fourth tone is provisioned. See the 
                        Administrator's Guide for a description of the tones."
                    ::= { endptSIP 64 }
endptSDPCAPNEG   OBJECT-TYPE
                    SYNTAX      INTEGER
                    MAX-ACCESS  read-only
                    STATUS      current
                    DESCRIPTION "Controls SDP capability negotiation. The variable returns a
                        1 (default) when capability negotiation is enabled and a 0 when
                        capability negotiation is disabled."
                    ::= { endptSIP 65 }
endptSIMULTANEOUSREGISTRATIONS   OBJECT-TYPE
                    SYNTAX      INTEGER
                    MAX-ACCESS  read-only
                    STATUS      current
                    DESCRIPTION "The number of Session Managers that the phone simultaneously
                        registers with. The variable returns a
                        3 (default), 2 or 1."
                    ::= { endptSIP 66 }
endptCONFERENCESERVERADDRESS         OBJECT-TYPE
                    SYNTAX      DisplayString
                    MAX-ACCESS  read-only
                    STATUS      current
                    DESCRIPTION "The address of the Avaya Aura Conference (AACS) R6.0 Server."
                    ::= { endptSIP 67 }
endptCONFERENCESERVERPORT   OBJECT-TYPE
                    SYNTAX      INTEGER
                    MAX-ACCESS  read-only
                    STATUS      current
                    DESCRIPTION "The AACS R6.0 destination port."
                    ::= { endptSIP 68 }
endptENABLESECUREHTTPFORCONFERENCINGSERVICE   OBJECT-TYPE
                    SYNTAX      INTEGER
                    MAX-ACCESS  read-only
                    STATUS      current
                    DESCRIPTION "Controls security of the AACS R6.0 communication. The variable
                        returns a 1 (default) when secure and 0 when insecure."
                    ::= { endptSIP 69 }
endptCONFERENCEBLUEPRINTINFO         OBJECT-TYPE
                    SYNTAX      DisplayString
                    MAX-ACCESS  read-only
                    STATUS      current
                    DESCRIPTION "AACS R6.0 Conference Blueprint information."
                    ::= { endptSIP 70 }
endptNODIGITSTIMEOUT   OBJECT-TYPE
                    SYNTAX      INTEGER
                    MAX-ACCESS  read-only
                    STATUS      current
                    DESCRIPTION "The time in seconds if no dialing digits are entered before 
                                 a user hears the re-order tone. The default is 20 seconds.
                                 The range is 1 to 60 seconds."
                    ::= { endptSIP 71 }
endptINTERDIGITTIMEOUT   OBJECT-TYPE
                    SYNTAX      INTEGER
                    MAX-ACCESS  read-only
                    STATUS      current
                    DESCRIPTION "This is the timeout that takes place when user stops inputing digits.
                                 The timeout is treated as digit collection, and when it occurs, the
                                 application sends out an INVITE. The default is 5 seconds, the range is 1 to 10 seconds."
                    ::= { endptSIP 72 }
endptENABLE3PCCENVIRONMENT   OBJECT-TYPE
                    SYNTAX      INTEGER
                    MAX-ACCESS  read-only
                    STATUS      current
                    DESCRIPTION "3PCC Environment mode - When this parameter set to 1, it indicates that the phone is
                                 functioning in a 3PCC environment (The other environment modes are IPO and Aura).
                                 Default value of this parameter is 1"
                    ::= {endptSIP 73 }
endptENABLESIPUSERID   OBJECT-TYPE
                    SYNTAX      INTEGER
                    MAX-ACCESS  read-only
                    STATUS      current
                    DESCRIPTION "when this parameter set to 1, it enables display of 'user id' field on the phone.
                                 User Id field information is used to authenticate the user.
                                 Default value for this parameter is 0"
                    ::= {endptSIP 74 }
endptENABLESTRICTUSERVALIDATION   OBJECT-TYPE
                    SYNTAX      INTEGER
                    MAX-ACCESS  read-only
                    STATUS      current
                    DESCRIPTION "Strict User Validation, when this parameter is set to 0 then 
                                 if request URI does not match with the domain name and if server replaces 
                                 request URI with WAN side IP address then phone does not send 3xx response. 
                                 It proceeds with the normal call flow. In 3PCC environment, server changes request URI. 
                                 Default value for this parameter is 0"
                    ::= {endptSIP 75 }
endptENABLEUDPTRANSPORT   OBJECT-TYPE
                    SYNTAX      INTEGER
                    MAX-ACCESS  read-only
                    STATUS      current
                    DESCRIPTION "UDP transport type, when this parameter is set to 1, UDP transport type will be
                                 provided as a transport type to choose in the phone. User can select it when configuring 
                                 manual proxy. Default value for this parameter is 0"
                    ::= {endptSIP 76 }
endptENABLEDND      OBJECT-TYPE
                    SYNTAX      INTEGER
                    MAX-ACCESS  read-only
                    STATUS      current
                    DESCRIPTION "Do Not Disturb,when this parameter is set to 1 this feature is on.Default value for this parameter is 1"
                    ::= {endptSIP 77 }
endptENABLEAUTOANSWERSUPPORT   OBJECT-TYPE
                    SYNTAX      INTEGER
                    MAX-ACCESS  read-only
                    STATUS      current
                    DESCRIPTION "Auto Answer Support is enabled when this parameter is set to 1. This feature enables the phone to 
                                 answer automatically.Default value for this parameter is 0"
                    ::= {endptSIP 78 }
endptENABLEDNDPRIORITYOVERCFUCFB   OBJECT-TYPE
                    SYNTAX      INTEGER
                    MAX-ACCESS  read-only
                    STATUS      current
                    DESCRIPTION "DND Priority Over CFU CFB, when this parameter is set to 1 then DND will have higher
                                 priority over call forward and call forward busy. Default value for this parameter is 0"
                    ::= {endptSIP 79 }
endptAUTOANSWERMUTEENABLE   OBJECT-TYPE
                    SYNTAX      INTEGER
                    MAX-ACCESS  read-only
                    STATUS      current
                    DESCRIPTION "Auto Answer Mute Enable - When this parameter is set to 1, phone is muted after auto answer. 
                                 Default value for this parameter is 1"
                    ::= {endptSIP 80 }
endptHOLDREMINDERTIMER   OBJECT-TYPE
                    SYNTAX      INTEGER
                    MAX-ACCESS  read-only
                    STATUS      current
                    DESCRIPTION "Set Hold Reminder Timer,is the time after which the user is reminded about a call
                                 on hold.The max value being 999. Default value for this parameter is 0"
                    ::= {endptSIP 81 }
endptUSERSTOREURI   OBJECT-TYPE
                    SYNTAX      DisplayString
                    MAX-ACCESS  read-only
                    STATUS      current
                    DESCRIPTION "User Store URI identifies the URL where user information (ex: contacts) can be stored. 
                                 Default value for this parameter is empty string"
                    ::= {endptSIP 82 }
endptSIPTIMERT1     OBJECT-TYPE
                    SYNTAX      INTEGER
                    MAX-ACCESS  read-only
                    STATUS      current
                    DESCRIPTION "Sip Timer T1. It is round trip time for an IP packet.
                                 Default value for this parameter is 500 milliseconds"
                    ::= {endptSIP 83 }
endptSIPTIMERT2     OBJECT-TYPE
                    SYNTAX      INTEGER
                    MAX-ACCESS  read-only
                    STATUS      current
                    DESCRIPTION "Sip Timer T2. It is maximum retransmit interval for Non-Invite request and Invite response.
                                 Default value for this parameter is 4000 milliseconds"
                    ::= {endptSIP 84 }
endptSIPTIMERT4     OBJECT-TYPE
                    SYNTAX      INTEGER
                    MAX-ACCESS  read-only
                    STATUS      current
                    DESCRIPTION "Sip Timer T4. It is maximum duration that a message remains in a network.
                                 Default value for this parameter is 5000 milliseconds"
                    ::= {endptSIP 85 }

endptENABLEIPOFFICE OBJECT-TYPE
                    SYNTAX      INTEGER
                    MAX-ACCESS  read-only
                    STATUS      current
                    DESCRIPTION "Specifies deployment mode of IP Office
                                Range: [0, 2]
                                Default: 0 
                                Values: 
                                    0 - not an IPO environment (Default) 
                                    1 - IPO environment
                                    2 - IPO with CCMS over SIP Configuration parameter  
                                "
                    ::= {endptSIP 86 } 

endptMEDIAPRESERVATION OBJECT-TYPE
                    SYNTAX      INTEGER
                    MAX-ACCESS  read-only
                    STATUS      current
                    DESCRIPTION "Determines if an active call will be preserved in CCMS mode.
                                Range: [0, 1]
                                Default: 1
                                Values: 
                                    0 - media preservation disabled 
                                    1 - media preservation enabled 
                                "
                    ::= {endptSIP 87 } 

endptPRESERVEDCALLDURATION OBJECT-TYPE
                    SYNTAX      INTEGER
                    MAX-ACCESS  read-only
                    STATUS      current
                    DESCRIPTION "Duration in minutes of preserved call in CCMS mode.
                                Range: [10, 120]
                                Default: 120
                                "
                    ::= {endptSIP 88 }
endptMEDIAADDRMODE  OBJECT-TYPE
                    SYNTAX      INTEGER
                    MAX-ACCESS  read-only
                    STATUS      current
                    DESCRIPTION "This parameter represents the phone's current configuration for media ANAT priority of outgoing calls:
                    64 - both ipv4/ipv6 are set up, ipv6 is prioritized;
                    46 - both ipv4/ipv6 are set up, ipv4 is prioritized;
                    4  - ipv4 only is set up;
                    6  - ipv6 only is set up."
                    ::= { endptSIP 89 }
endptSIGNALINGADDRMODE  OBJECT-TYPE
                    SYNTAX      INTEGER
                    MAX-ACCESS  read-only
                    STATUS      current
                    DESCRIPTION "This parameter represents the phone's current configuration for signaling address mode:
                    4 - SIP signaling set up for ipv4;
                    6 - SIP signaling set up for ipv6."
                    ::= { endptSIP 90 }
endptDHCPSTAT       OBJECT-TYPE
                    SYNTAX      INTEGER
                    MAX-ACCESS  read-only
                    STATUS      current
                    DESCRIPTION "This parameter represents the phone's current configuration for dhcpstat:
                    1 - DHCPv4 only client;
                    2 - DHCPv6 only client;
                    3 - run both DHCPv4 & DHCPv6 client."
                    ::= { endptSIP 91 }
endptIPADDV6        OBJECT-TYPE
                    SYNTAX      DisplayString
                    MAX-ACCESS  read-only
                    STATUS      current
                    DESCRIPTION "This parameter represents the phone's current ipv6 global addresses list."
                    ::= { endptSIP 92 }
endptIPADDV6LL      OBJECT-TYPE
                    SYNTAX      DisplayString
                    MAX-ACCESS  read-only
                    STATUS      current
                    DESCRIPTION "This parameter represents the phone's current configuration for own link local ipv6 address."
                    ::= { endptSIP 93 }
endptIPV6STAT       OBJECT-TYPE
                    SYNTAX      INTEGER
                    MAX-ACCESS  read-only
                    STATUS      current
                    DESCRIPTION "This parameter represents the phone's current configuration for ipv6 mode:
                    0 - IPv6 module is disabled;
                    1 - IPv6 is enabled."
                    ::= { endptSIP 94 }
endptIPMODE         OBJECT-TYPE
                    SYNTAX      INTEGER
                    MAX-ACCESS  read-only
                    STATUS      current
                    DESCRIPTION "This parameter represents the phone's current configuration for ip mode:
                    0 - initial value and value for indicating error when there are no assigned ip addresses;
                    1 - IPv4 only;
                    2 - IPv6 only;
                    3 - dual mode."
                    ::= { endptSIP 95 }
endptIPV6DADXMITS   OBJECT-TYPE
                    SYNTAX      INTEGER
                    MAX-ACCESS  read-only
                    STATUS      current
                    DESCRIPTION "This parameter represents the phone's current configuration for DAD - duplicate address detection:
                    0 - DAD disabled;
                    1 - Send 1 NS for DAD;
                    2 - Send 2 NS for DAD;
                    3 - Send 3 NS for DAD;
                    4 - Send 4 NS for DAD;
                    5 - Send 5 NS for DAD."
                    ::= { endptSIP 96 }

endptDHCPSTD        OBJECT-TYPE
                    SYNTAX      INTEGER
                    MAX-ACCESS  read-only
                    STATUS      current
                    DESCRIPTION "DHCP Lease Violation Flag:
                    0 - Use expired DHCP address until reset or conflict;
                    1 - Do not use expired DHCP addresses."
                    ::= { endptSIP 97 }              

endptPRIMARYLINE    OBJECT-TYPE
                    SYNTAX      INTEGER
                    MAX-ACCESS  read-only
                    STATUS      current
                    DESCRIPTION "Specifies if the phones primary line is a private or shared line. 
                    The primary line is the one associated with the user's login credentials.
                    '0' Primary line is a private line (default)
                    '1' Primary line is a shared line"
                    ::= { endptSIP 98 }

endptLINESEIZEDURATION OBJECT-TYPE
                    SYNTAX      INTEGER
                    MAX-ACCESS  read-only
                    STATUS      current
                    DESCRIPTION "Defines the length of time that a shared line will stay off hook with dial tone when the call appearance is 
                        'seized' before the line will transition to a failed state. This is the exact value used to define the 
                        'expires' value for 'line-seize' subscriptions. 
                        In Ring Central environment, this parameter is also used for outbound dialog event subscription expiry time since
                        line seize shares same subscription as outbound dialog event subscrption."  
                    ::= { endptSIP 99 }  

endptSHAREDLINE1ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 100 }
          
endptSHAREDLINE2ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 101 }

endptSHAREDLINE3ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 102 }

endptSHAREDLINE1MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 103 }

endptSHAREDLINE2MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 104 }

endptSHAREDLINE3MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 105 }

endptSHAREDLINE1SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 106 }

endptSHAREDLINE2SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 107 }

endptSHAREDLINE3SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 108 }

endptSHAREDLINE1USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA1_SIPUSERID would be used for authentication.
                    The setting only applies to 3PCC server environments.
                    Not used for BLA, BCA."
                    ::= { endptSIP 109 }

endptSHAREDLINE2USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA2_SIPUSERID would be used for authentication.
                    The setting only applies to 3PCC server environments."
                    ::= { endptSIP 110 }

endptSHAREDLINE3USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA3_SIPUSERID would be used for authentication.
                    The setting only applies to 3PCC server environments."
                    ::= { endptSIP 111 }

endptSHAREDLINE1EXTENSION  OBJECT-TYPE
                    SYNTAX      DisplayString (SIZE(0..255))
                    MAX-ACCESS  read-only
                    STATUS      current
                    DESCRIPTION "The display name for the shared line. If not specified the SCA1_SIPUSERID would be used.
                    The setting only applies to 3PCC server environments."
                    ::= { endptSIP 112 }

endptSHAREDLINE2EXTENSION  OBJECT-TYPE
                    SYNTAX      DisplayString (SIZE(0..255))
                    MAX-ACCESS  read-only
                    STATUS      current
                    DESCRIPTION "The display name for the shared line. If not specified the SCA2_SIPUSERID would be used.
                    The setting only applies to 3PCC server environments."
                    ::= { endptSIP 113 }

endptSHAREDLINE3EXTENSION  OBJECT-TYPE
                    SYNTAX      DisplayString (SIZE(0..255))
                    MAX-ACCESS  read-only
                    STATUS      current
                    DESCRIPTION "The display name for the shared line. If not specified the SCA3_SIPUSERID would be used.
                    The setting only applies to 3PCC server environments."
                    ::= { endptSIP 114 }

endptSHAREDLINE1BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 115 }

endptSHAREDLINE2BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 116 }

endptSHAREDLINE3BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 117 }

endptSIPCONTROLLERSINFORMATION  OBJECT-TYPE
                    SYNTAX      DisplayString
                    MAX-ACCESS  read-only
                    STATUS      current
                    DESCRIPTION "This object is used to display sip controllers 
                    information for 3PCC modes (Generic, Broadsoft, 3CX or Netsapiens). 
                    It displays the information as follows:
                    User's Domain: [ Controller Fqdn1:[IPaddress1:Protocol:Port:$Priority:$Status, IPaddress2:Protocol:Port:$Priority:$Status]]  
                    User's domain - sip user's domain
                    Where 'Controller Fqdn1' would be resolved to 
                    IP Address1 and IP Address 2 through DNS.
                    Priority indicates whether the server is primary or secondary."
                    ::= { endptSIP 118 }

endptPRIMARYLINEBARGEINENABLED  OBJECT-TYPE
                    SYNTAX      INTEGER
                    MAX-ACCESS  read-only
                    STATUS      current
                    DESCRIPTION "A primary line which is shared can be configured in the Broadsoft server to 
                    either enable or disable the ability of a user to barge into a call at a different location on the shared line.
                    This setting is ignored if PRIMARY_LINE_TYPE = 0
                    Not used for RingCentral and Avaya Cloud.
                    '0' Barge in is disabled for the shared line
                    '1' Barge in is enabled for the shared line (default)"
                    ::= { endptSIP 119 }

endptPROVIDESHAREDLINECONFIG  OBJECT-TYPE
                    SYNTAX      INTEGER
                    MAX-ACCESS  read-only
                    STATUS      current
                    DESCRIPTION "Specifies if the user has the ability to change Shared Line configuration using the Settings menu on the phone.
                    Not used for RingCentral and Avaya Cloud.
                    '0' Shared lines is not displayed in settings menu
                    '1' Shared lines is displayed in settings menu but all information is read-only
                    '2' Shared lines is displayed in settings menu and is fully configurable"
                    ::= { endptSIP 120 }

endptSHAREDLINERINGTYPES  OBJECT-TYPE
                    SYNTAX      DisplayString (SIZE(0..255))
                    MAX-ACCESS  read-only
                    STATUS      current
                    DESCRIPTION "Stores personalized ringtones for SCA lines"
                    ::= { endptSIP 121 }

endptSELECTEDSERVERMODE  OBJECT-TYPE
                    SYNTAX      INTEGER
                    MAX-ACCESS  read-only
                    STATUS      current
                    DESCRIPTION "Internal parameter indicating current operational mode.
                    Value - Operation
                    0 - Invalid
                    1 - Aura
                    2 - 3PCC Generic
                    3 - IPO
                    4 - IPO with CCMS support
                    5 - 3PCC with Broadsoft support
                    6 - 3CX
                    7 - Netsapiens
                    8 - RCO
                    9 - ACO"
                    ::= { endptSIP 122 }

endptDUALIPPREF  OBJECT-TYPE
                    SYNTAX      INTEGER
                    MAX-ACCESS  read-only
                    STATUS      current
                    DESCRIPTION "DUAL_IPPREF controls:
                        - the selection of SSON either from DHCPv4 or DHCPv6 server, when phone is in dual mode, and
                        - whether an IPv4 or IPv6 addresses returned by DNS would be tried first during dual-mode operation.
                    DHCP clients use DUAL_IPPREF to decide which SSON configuration attributes to apply for DHCPv4/DHCPv6 interworking in dual mode. 
                    Based on DUAL_IPPREF the phone selects SSON attributes either from DHCPv4 or DHCPv6 server.
                    If DNS server name is provided, and if DNS resolver returns both IPv4 and IPv6 addresses, 
                    the order in which they will be tried will be based on DUAL_IPPREF parameter.
                    NOTE: SIP server FQDNs are resolved into addresses that are ordered based on SIGNALING_ADDR_MODE, not DUAL_IPPREF
                    Value - Operation
                        4 - IPv4 preference (default)
                        6 - IPv6 preference"
                    ::= { endptSIP 123 }

endptDHCPSTDV6  OBJECT-TYPE
                    SYNTAX      INTEGER
                    MAX-ACCESS  read-only
                    STATUS      current
                    DESCRIPTION "DHCPV6 extended rebind flag.
                    DHCPSTDV6 specifies whether DHCPv6 will comply with the IETF RFC 3155 standard and immediately stop using an 
                    IPv6 address if the the address valid lifetime expires, or whether it will enter an extended rebinding state 
                    in which it continues to use the address and to periodically send a rebinding request, as well as to periodically
                    send an NS (Neighbor Solicitation) request to check for address conflicts, until a REPLY response is received from
                    a DHCPv6 server  (either a new address, or zero lifetimes, or error status codes) or until a DAD conflict is detected.
                    If the address is duplicated, DHCPv6 client restarts and solicits for a new address.
                    Value - Operation
                        0 - enter proprietary extended rebinding state (continue to use IPv6 address, if DHCPv6 lease expires) (default)
                        1 - comply with DHCPv6 standard (immediately release IPv6 address, if DHCPv6 lease expires)"
                    ::= { endptSIP 124 }

endptREUSETIMER  OBJECT-TYPE
                    SYNTAX      INTEGER
                    MAX-ACCESS  read-only
                    STATUS      current
                    DESCRIPTION "REUSETIME specifies the number of seconds that DHCPV4 or DHCPv6 discovery will be attempted before either:
                        - reusing the previously cached value of IPv4 address (and associated address information) that the Phone had the 
                          last time successfully registered with a call server, if such an address is available, or
                        - continue discovery DHCPv6 server: IPv6 does not support reuse, so there is no corresponding parameter to IPv4's REUSE_IPADD.
                    While reusing an address, DHCPV4 will enter the extended rebinding state described for DHCPSTD.
                    Valid values are 0 and 20 through 999; the default value is 60.
                    A value of zero means that DHCP or DHCPv6 will be tried forever (i.e., no reuse).
                    Valid Values: 0 and 20 through 999 (60 is default)"
                    ::= { endptSIP 125 }

endptPRIVACYSLAACMODE  OBJECT-TYPE
                    SYNTAX      INTEGER
                    MAX-ACCESS  read-only
                    STATUS      current
                    DESCRIPTION "Specifies the preference for Privacy Extensions(RFC3041)
                    Value - Operation
                        1 - Privacy extension disabled, one stable address is generated using modified EUI-64 format interface identifier 
                          (Based on MAC address). The phone address selection preference is based on default RFC6724 SASA rules.
                        2 - Privacy extension enabled, one stable address is generated using modified EUI-64 format interface identifier 
                           (Based on MAC address) and one temporary private address is generated. The phone address selection preference 
                           is based on RFC6724 SASA rules. PRIVACY_SLAAC_MODE changes default SASA rules (i.e. Rule 7) to prefer a manual,
                           DHCPv6 or Stable SLAAC over SLAAC temporary address. (default)
                        3 - Privacy extension enabled, one stable address is generated using modified EUI-64 format interface identifier 
                           (Based on MAC address) and one temporary private IPv6 address is generated. The phone address selection 
                           preference is based on default RFC6724 SASA rules. Default SASA Rule 7 is used to prefer SLAAC temporary address 
                           over a manual, DHCPv6 or Stable SLAAC addresses"
                    ::= { endptSIP 126 }

endptSIPCONTROLLERLIST2  OBJECT-TYPE
                    SYNTAX      DisplayString
                    MAX-ACCESS  read-only
                    STATUS      current
                    DESCRIPTION "This parameter replaces  SIP_CONTROLLER_LIST for dual mode phones. It is used on IPv6-only phones to provide
                    the list of SIPv6 servers. SIPv4 servers are ignored in IPv6-only mode. It is used to select the registration address.
                    The list has the following format: host[:port][;transport=xxx] where:
                      -host: is an IP addresses in dotted-decimal format or hex format
                      -port:is the optional port number. If a port number is not specified the default value (5060 for TCP, 5061 for TLS) will be used
                      -transport: is the optional transport type (where xxx is TLS or TCP)
                    If a transport type is not specified the default value TLS will be used
                    A dual mode controller has addresses of both families within curly brackets.
                    Dual mode phones use SIGNALING_ADDR_MODE to select SM IP addresses from SIP_CONTROLLER_LIST_2.
                    If SIGNALING_ADDR_MODE is 4, register to the first IPv4 address in SIP_CONTROLLER_LIST_2.
                    IPv4-only phones use SIP_CONTROLLER_LIST. Dual mode phones use SIP_CONTROLLER_LIST if SIP_CONTROLLER_LIST_2 is not provided.
                      Valid Values: String The comma separated list of SIP proxy/registrar servers
                      0 to 255 characters: zero or more IP addresses in dotted decimal or colon-hex format, 
                      separated by commas without any intervening spaces.
                      Default: (null)"
                    ::= { endptSIP 127 }

endptSCEPENCALG  OBJECT-TYPE
                    SYNTAX      INTEGER
                    MAX-ACCESS  read-only
                    STATUS      current
                    DESCRIPTION "SCEP Encryption Algorithm
                      Value - Operation
                        0 - DES
                        1 - AES-256"
                    ::= { endptSIP 128 }

endptBLOCKCERTIFICATEWILDCARDS  OBJECT-TYPE
                    SYNTAX      INTEGER
                    MAX-ACCESS  read-only
                    STATUS      current
                    DESCRIPTION "Flag indicating accepting wildcards in certificate.
                      Value - Operation
                        0 - Accept wildcards in certificate
                        1 - Do not accept wildcards in certificates"
                    ::= { endptSIP 129 }

endptMAXDNSDISCOVEREDSIPCONTROLLERS  OBJECT-TYPE
                    SYNTAX      INTEGER
                    MAX-ACCESS  read-only
                    STATUS      current
                    DESCRIPTION "Specifies maximum number of sip controllers to be used for redundancy from DNS lookups.
                        For Netsapiens mode it is accepted to take value between 2 and 6.
                        Parameter takes effect only when 3PCC_SERVER_MODE = 3 (Netsapiens), for Broadsoft number of controllers is always 2, for other modes it's 1."
                    ::= { endptSIP 130 }

endptSCEPENTITYCLASS  OBJECT-TYPE
                    SYNTAX      DisplayString
                    MAX-ACCESS  read-only
                    STATUS      current
                    DESCRIPTION "SCEP entity class. This variable returns  
                    a string used as entity class when using SMGR SCEP.
                    Default: (null)"
                    ::= { endptSIP 131 }

endptAUTOANSWERDURINGCALL  OBJECT-TYPE
                    SYNTAX      INTEGER
                    MAX-ACCESS  read-only
                    STATUS      current
                    DESCRIPTION "Specifies flag that can be used by the phone to define behavior for auto-answer calls during another active call. If value is 0 then auto-answer call should not be answered during current active call. If value is 1 then current active call should be put on hold and incoming auto-answer call should be answered automatically"
                    ::= { endptSIP 132 }

endptSOFTKEYACTIVE  OBJECT-TYPE
                    SYNTAX      DisplayString
                    MAX-ACCESS  read-only
                    STATUS      current
                    DESCRIPTION "DTMF softkey."
                    ::= { endptSIP 133 }

endptDISPLAYNAME    OBJECT-TYPE
                    SYNTAX      DisplayString
                    MAX-ACCESS  read-only
                    STATUS      current
                    DESCRIPTION "This parameter will be used as the display name for the remote party if the server supports a phone providing 
                    its own display name, and it is also displayed as part of appearance context (when appearance context is enabled) in
                    phone screen application header line.
                    Parameter is applied only in 3PCC envirnoment."
                    ::= { endptSIP 134 }

endptSHAREDLINEMODE OBJECT-TYPE
                    SYNTAX      INTEGER
                    MAX-ACCESS  read-only
                    STATUS      current
                    DESCRIPTION "Specifies Shared Line Mode, there are three options: 0 (SCA), 1 (BLA) or 2 (BCA) mode.
                    The setting only applies to 3PCC server environments."
                    ::= { endptSIP 135 }  
                    
endptSHAREDLINE4ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 136 }

endptSHAREDLINE5ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 137 }

endptSHAREDLINE6ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 138 }

endptSHAREDLINE7ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 139 }

endptSHAREDLINE8ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 140 }

endptSHAREDLINE4MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 141 }

endptSHAREDLINE5MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 142 }

endptSHAREDLINE6MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 143 }

endptSHAREDLINE7MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 144 }

endptSHAREDLINE8MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 145 }

endptSHAREDLINE4SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 146 }

endptSHAREDLINE5SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 147 }

endptSHAREDLINE6SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 148 }

endptSHAREDLINE7SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 149 }

endptSHAREDLINE8SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 150 }

endptSHAREDLINE4USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA4_SIPUSERID would be used for authentication.
                    The setting only applies to 3PCC server environments."
                    ::= { endptSIP 151 }

endptSHAREDLINE5USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA5_SIPUSERID would be used for authentication.
                    The setting only applies to 3PCC server environments."
                    ::= { endptSIP 152 }

endptSHAREDLINE6USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA6_SIPUSERID would be used for authentication.
                    The setting only applies to 3PCC server environments."
                    ::= { endptSIP 153 }

endptSHAREDLINE7USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA7_SIPUSERID would be used for authentication.
                    The setting only applies to 3PCC server environments."
                    ::= { endptSIP 154 }

endptSHAREDLINE8USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA8_SIPUSERID would be used for authentication.
                    The setting only applies to 3PCC server environments."
                    ::= { endptSIP 155 }

endptSHAREDLINE4EXTENSION  OBJECT-TYPE
                    SYNTAX      DisplayString (SIZE(0..255))
                    MAX-ACCESS  read-only
                    STATUS      current
                    DESCRIPTION "The display name for the shared line. If not specified the SCA4_SIPUSERID would be used.
                    The setting only applies to 3PCC server environments."
                    ::= { endptSIP 156 }

endptSHAREDLINE5EXTENSION  OBJECT-TYPE
                    SYNTAX      DisplayString (SIZE(0..255))
                    MAX-ACCESS  read-only
                    STATUS      current
                    DESCRIPTION "The display name for the shared line. If not specified the SCA5_SIPUSERID would be used.
                    The setting only applies to 3PCC server environments."
                    ::= { endptSIP 157 }

endptSHAREDLINE6EXTENSION  OBJECT-TYPE
                    SYNTAX      DisplayString (SIZE(0..255))
                    MAX-ACCESS  read-only
                    STATUS      current
                    DESCRIPTION "The display name for the shared line. If not specified the SCA6_SIPUSERID would be used.
                    The setting only applies to 3PCC server environments."
                    ::= { endptSIP 158 }

endptSHAREDLINE7EXTENSION  OBJECT-TYPE
                    SYNTAX      DisplayString (SIZE(0..255))
                    MAX-ACCESS  read-only
                    STATUS      current
                    DESCRIPTION "The display name for the shared line. If not specified the SCA7_SIPUSERID would be used.
                    The setting only applies to 3PCC server environments."
                    ::= { endptSIP 159 }

endptSHAREDLINE8EXTENSION  OBJECT-TYPE
                    SYNTAX      DisplayString (SIZE(0..255))
                    MAX-ACCESS  read-only
                    STATUS      current
                    DESCRIPTION "The display name for the shared line. If not specified the SCA8_SIPUSERID would be used.
                    The setting only applies to 3PCC server environments."
                    ::= { endptSIP 160 }

endptSHAREDLINE4BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 161 }

endptSHAREDLINE5BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 162 }

endptSHAREDLINE6BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 163 }

endptSHAREDLINE7BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 164 }

endptSHAREDLINE8BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 165 }

endptENABLESIPURIHOSTVALIDATION  OBJECT-TYPE
                    SYNTAX      INTEGER
                    MAX-ACCESS  read-only
                    STATUS      current
                    DESCRIPTION "Allows accepting SIP URI with unrecognized host part in INVITE message.
                    Ranges 0 - 1 (default)."
                    ::= { endptSIP 166 }

endptCALLFWDCHAINORDER  OBJECT-TYPE
                    SYNTAX      INTEGER
                    MAX-ACCESS  read-only
                    STATUS      current
                    DESCRIPTION "Forwarded by details are shown for incoming calls that have been forwarded by another user.
                    CALLFWD_CHAIN_ORDER specifies which user information is displayed on an incoming call if there have been multiple forwards before being received as an incoming call.
                    '0' (Default) - the first CFWD party is displayed
                    '1' - the last CFWD party is displayed"
                    ::= { endptSIP 167 }

endptSHAREDLINE1INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 168 }

endptSHAREDLINE2INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 169 }

endptSHAREDLINE3INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 170 }

endptSHAREDLINE4INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 171 }

endptSHAREDLINE5INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 172 }

endptSHAREDLINE6INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 173 }

endptSHAREDLINE7INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 174 }

endptSHAREDLINE8INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 175 }

endptSHAREDLINE1INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 176 }

endptSHAREDLINE2INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 177 }

endptSHAREDLINE3INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 178 }

endptSHAREDLINE4INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 179 }

endptSHAREDLINE5INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 180 }

endptSHAREDLINE6INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 181 }

endptSHAREDLINE7INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 182 }

endptSHAREDLINE8INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 183 }

endptSHAREDCALLAPPEARANCESMODE  OBJECT-TYPE
                    SYNTAX      INTEGER
                    MAX-ACCESS  read-only
                    STATUS      current
                    DESCRIPTION "Specifies behaviour of Shared Call Appearances for all Shared Lines.
                    This parameter should only be used if SHARED_LINE_MODE is BLA
                    Values
                    0 - (Default) Phone screen shows 1 Shared Call Appearance and Call Appearance can perform Blind Transfer only
                    1 - Phone screen shows 1 Shared Call Appearance and Call Appearance can perform Blind Transfer, Consult Transfer and Conference calls."
                    ::= { endptSIP 184 }

endptENABLEHOLDREMINDERDISPLAY  OBJECT-TYPE
                    SYNTAX      INTEGER
                    MAX-ACCESS  read-only
                    STATUS      current
                    DESCRIPTION "Specifies whether to display  hc [Return] on call appearance when the phone reminds the user about a held call
                    This parameter is only for OpenSIP environments.
                    0 - called party name / number will be displayed on call appearance when the phone reminds the user about a held call
                    1 - (Default) called party name / number with hc [Return] would be displayed on call appearance when the phone reminds the user about a held call"
                    ::= { endptSIP 185 }

endptSOFTKEYIDLE  OBJECT-TYPE
                    SYNTAX      DisplayString
                    MAX-ACCESS  read-only
                    STATUS      current
                    DESCRIPTION "Describes new custom softkey for Primary CA lines in IDLE state."
                    ::= { endptSIP 186 }

endptSOFTKEYACTIVECUST  OBJECT-TYPE
                    SYNTAX      DisplayString
                    MAX-ACCESS  read-only
                    STATUS      current
                    DESCRIPTION "Describes new custom softkey for Primary CA lines in ACTIVE state."
                    ::= { endptSIP 187 }

endptSOFTKEYINCOMINGVISUAL  OBJECT-TYPE
                    SYNTAX      DisplayString
                    MAX-ACCESS  read-only
                    STATUS      current
                    DESCRIPTION "Describes new custom softkey for Primary CA lines in INCOMING_VISUAL state."
                    ::= { endptSIP 188 }

endptSOFTKEYINCOMING  OBJECT-TYPE
                    SYNTAX      DisplayString
                    MAX-ACCESS  read-only
                    STATUS      current
                    DESCRIPTION "Describes new custom softkey for Primary CA lines in INCOMING state."
                    ::= { endptSIP 189 }

endptSOFTKEYOUTGOING  OBJECT-TYPE
                    SYNTAX      DisplayString
                    MAX-ACCESS  read-only
                    STATUS      current
                    DESCRIPTION "Describes new custom softkey for Primary CA lines in OUTGOING state."
                    ::= { endptSIP 190 }

endptSOFTKEYACTIVEPAGETARGET  OBJECT-TYPE
                    SYNTAX      DisplayString
                    MAX-ACCESS  read-only
                    STATUS      current
                    DESCRIPTION "Describes new custom softkey for Primary CA lines in ACTIVE PAGE state."
                    ::= { endptSIP 191 }

endptOVERRIDESOFTKEYIDLE  OBJECT-TYPE
                    SYNTAX      INTEGER
                    MAX-ACCESS  read-only
                    STATUS      current
                    DESCRIPTION "Determines if default softkeys will be shown for Primary CA lines in IDLE state.
                    0 (Default) - default softkeys will be shown.
                    1 - default softkeys will NOT be shown."
                    ::= { endptSIP 192 }

endptOVERRIDESOFTKEYACTIVE  OBJECT-TYPE
                    SYNTAX      INTEGER
                    MAX-ACCESS  read-only
                    STATUS      current
                    DESCRIPTION "Determines if default softkeys will be shown for Primary CA lines in ACTIVE state.
                    0 (Default) - default softkeys will be shown.
                    1 - default softkeys will NOT be shown."
                    ::= { endptSIP 193 }

endptOVERRIDESOFTKEYINCOMINGVISUAL  OBJECT-TYPE
                    SYNTAX      INTEGER
                    MAX-ACCESS  read-only
                    STATUS      current
                    DESCRIPTION "Determines if default softkeys will be shown for Primary CA lines in INCOMING_VISUAL state.
                    0 (Default) - default softkeys will be shown.
                    1 - default softkeys will NOT be shown."
                    ::= { endptSIP 194 }

endptOVERRIDESOFTKEYINCOMING  OBJECT-TYPE
                    SYNTAX      INTEGER
                    MAX-ACCESS  read-only
                    STATUS      current
                    DESCRIPTION "Determines if default softkeys will be shown for Primary CA lines in INCOMING state.
                    0 (Default) - default softkeys will be shown.
                    1 - default softkeys will NOT be shown."
                    ::= { endptSIP 195 }

endptOVERRIDESOFTKEYOUTGOING  OBJECT-TYPE
                    SYNTAX      INTEGER
                    MAX-ACCESS  read-only
                    STATUS      current
                    DESCRIPTION "Determines if default softkeys will be shown for Primary CA lines in OUTGOING state.
                    0 (Default) - default softkeys will be shown.
                    1 - default softkeys will NOT be shown."
                    ::= { endptSIP 196 }

endptOVERRIDESOFTKEYACTIVEPAGETARGET  OBJECT-TYPE
                    SYNTAX      INTEGER
                    MAX-ACCESS  read-only
                    STATUS      current
                    DESCRIPTION "Determines if default softkeys will be shown for Primary CA lines in ACTIVE PAGE state.
                    0 (Default) - default softkeys will be shown.
                    1 - default softkeys will NOT be shown."
                    ::= { endptSIP 197 }

endptSOFTKEYBLFIDLE  OBJECT-TYPE
                    SYNTAX      DisplayString
                    MAX-ACCESS  read-only
                    STATUS      current
                    DESCRIPTION "Describes new custom softkey for BLF lines in IDLE state."
                    ::= { endptSIP 198 }

endptSOFTKEYBLFACTIVE  OBJECT-TYPE
                    SYNTAX      DisplayString
                    MAX-ACCESS  read-only
                    STATUS      current
                    DESCRIPTION "Describes new custom softkey for BLF lines in ACTIVE state."
                    ::= { endptSIP 199 }

endptSOFTKEYBLFINCOMINGVISUAL  OBJECT-TYPE
                    SYNTAX      DisplayString
                    MAX-ACCESS  read-only
                    STATUS      current
                    DESCRIPTION "Describes new custom softkey for BLF lines in ALERTING state on the incoming call view."
                    ::= { endptSIP 200 }

endptSOFTKEYBLFINCOMING  OBJECT-TYPE
                    SYNTAX      DisplayString
                    MAX-ACCESS  read-only
                    STATUS      current
                    DESCRIPTION "Describes new custom softkey for BLF lines in ALERTING state."
                    ::= { endptSIP 201 }

endptSOFTKEYBLFOUTGOING  OBJECT-TYPE
                    SYNTAX      DisplayString
                    MAX-ACCESS  read-only
                    STATUS      current
                    DESCRIPTION "Describes new custom softkey for BLF lines in OUTGOING_RING state."
                    ::= { endptSIP 202 }

endptOVERRIDESOFTKEYBLFIDLE  OBJECT-TYPE
                    SYNTAX      INTEGER
                    MAX-ACCESS  read-only
                    STATUS      current
                    DESCRIPTION "Determines if default softkeys will be shown for BLF lines in IDLE state.
                    0 (Default) - default softkeys will be shown.
                    1 - default softkeys will NOT be shown."
                    ::= { endptSIP 203 }

endptOVERRIDESOFTKEYBLFACTIVE  OBJECT-TYPE
                    SYNTAX      INTEGER
                    MAX-ACCESS  read-only
                    STATUS      current
                    DESCRIPTION "Determines if default softkeys will be shown for BLF lines in ACTIVE state.
                    0 (Default) - default softkeys will be shown.
                    1 - default softkeys will NOT be shown."
                    ::= { endptSIP 204 }

endptOVERRIDESOFTKEYBLFINCOMINGVISUAL  OBJECT-TYPE
                    SYNTAX      INTEGER
                    MAX-ACCESS  read-only
                    STATUS      current
                    DESCRIPTION "Determines if default softkeys will be shown for BLF lines in ALERTING state on the incoming call view
                    0 (Default) - default softkeys will be shown.
                    1 - default softkeys will NOT be shown."
                    ::= { endptSIP 205 }

endptOVERRIDESOFTKEYBLFINCOMING  OBJECT-TYPE
                    SYNTAX      INTEGER
                    MAX-ACCESS  read-only
                    STATUS      current
                    DESCRIPTION "Determines if default softkeys will be shown for BLF lines in ALERTING state.
                    0 (Default) - default softkeys will be shown.
                    1 - default softkeys will NOT be shown."
                    ::= { endptSIP 206 }

endptOVERRIDESOFTKEYBLFOUTGOING  OBJECT-TYPE
                    SYNTAX      INTEGER
                    MAX-ACCESS  read-only
                    STATUS      current
                    DESCRIPTION "Determines if default softkeys will be shown for BLF lines in OUTGOING_RING state.
                    0 (Default) - default softkeys will be shown.
                    1 - default softkeys will NOT be shown."
                    ::= { endptSIP 207 }

endptSHAREDLINE1INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 208 }

endptSHAREDLINE2INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 209 }

endptSHAREDLINE3INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 210 }

endptSHAREDLINE4INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 211 }

endptSHAREDLINE5INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 212 }

endptSHAREDLINE6INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 213 }

endptSHAREDLINE7INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 214 }

endptSHAREDLINE8INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 215 }

endptSHAREDLINE1INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 216 }

endptSHAREDLINE2INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 217 }

endptSHAREDLINE3INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 218 }

endptSHAREDLINE4INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 219 }

endptSHAREDLINE5INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 220 }

endptSHAREDLINE6INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 221 }

endptSHAREDLINE7INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 222 }

endptSHAREDLINE8INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 223 }

endptBEACONINDICATIONMODE OBJECT-TYPE
                    SYNTAX      INTEGER
                    MAX-ACCESS  read-only
                    STATUS      current
                    DESCRIPTION "Specifies how a Beacon Led behaves at incoming call:
                    0 - Immediate, beacon led will flash immediately, when there is an incoming call and until call is answered.
                    1 - Delayed, beacon led will flash after a delay as per delayed ringing configuration, when there is an incoming call and until call is answered or ignored.
                    Applies to primary, shared, BLF and BLF park lines.
                    Default: 0"
                    ::= { endptSIP 224 }
									
endptVVMMODE OBJECT-TYPE
                    SYNTAX      INTEGER
                    MAX-ACCESS  read-only
                    STATUS      current
                    DESCRIPTION "Allows user to access Voice Mail service and receive a visual view of Inbox on the phone. If the feature is enabled user can play, read, delete voicemails from the phone.
                    Range: 0 - 1
                    Default: 0"
                    ::= { endptSIP 225 }
									
endptVVMPASSCODEREQ OBJECT-TYPE
                    SYNTAX      INTEGER
                    MAX-ACCESS  read-only
                    STATUS      current
                    DESCRIPTION "Specifies whether a voicemail PIN is required to access Visual voicemail box.
                    Range: 0 - 1
                    Default: 1"
                    ::= { endptSIP 226 }
									
endptVVMPLAYBACKNUM  OBJECT-TYPE
                    SYNTAX      DisplayString (SIZE(0..255))
                    MAX-ACCESS  read-only
                    STATUS      current
                    DESCRIPTION "Defines a phone number for Visual voicemail playback feature."
                    ::= { endptSIP 227 }

endptENABLEUSBHEADSET OBJECT-TYPE
                    SYNTAX      INTEGER
                    MAX-ACCESS  read-only
                    STATUS      current
                    DESCRIPTION "Enable or disable USB Headset.
                    Range: 0 - 1
                    Default: 1"
                    ::= { endptSIP 228 }
									
endptAGTGREETINGSTAT OBJECT-TYPE
                    SYNTAX      INTEGER
                    MAX-ACCESS  read-only
                    STATUS      current
                    DESCRIPTION "Enable or Disable Agent Greetings feature.
                    Range: 0 - 1
                    Default: 0"
                    ::= { endptSIP 229 }
									
endptAGTGREETLOGOUTDEL OBJECT-TYPE
                    SYNTAX      INTEGER
                    MAX-ACCESS  read-only
                    STATUS      current
                    DESCRIPTION "Delete Agent Greetings data by Agent logout or not.
                    Range: 0 - 1
                    Default: 0"
                    ::= { endptSIP 230 }
									
endptAGENTGREETINGSDELAY OBJECT-TYPE
                    SYNTAX      INTEGER
                    MAX-ACCESS  read-only
                    STATUS      current
                    DESCRIPTION "The delay between call answering and Agent Greeting playback in milliseconds.
                    Range: 0-3000
                    Default: 700"
                    ::= { endptSIP 231 }
									
endptENABLERANDOMRTPPORT OBJECT-TYPE
                    SYNTAX      INTEGER
                    MAX-ACCESS  read-only
                    STATUS      current
                    DESCRIPTION "If the value is 0, even numbered RTP ports starting at RTP_PORT_LOW will be used for all calls.
                    If the value is 1, an even numbered RTP port will be randomly selected in the range from RTP_PORT_LOW to RTP_PORT_LOW+RTP_PORT_RANGE each time audio path is established (e.g. when a call is answered or a call is resumed). To maximize the effectiveness of this setting, RTP_PORT_RANGE should be assigned a value much larger than the default of 40.
                    Default: 0"
                    ::= { endptSIP 232 }
									
endptSHAREDLINE9ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 233 }

endptSHAREDLINE10ENABLED OBJECT-TYPE
                    SYNTAX      INTEGER
                    MAX-ACCESS  read-only
                    STATUS      current
                    DESCRIPTION "Specifies if shared line is enabled.
                    The setting only applies to 3PCC server environments.
                    '0' The shared line is disabled (default)
                    '1' The shared line is enabled"
                    ::= { endptSIP 234 }

endptSHAREDLINE9MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 235 }

endptSHAREDLINE10MAXCALLAPPEARANCES  OBJECT-TYPE
                    SYNTAX      INTEGER
                    MAX-ACCESS  read-only
                    STATUS      current
                    DESCRIPTION "The number of call appearances the shared line can have.
                    Not used for BLA.
                    Range: 1-8
                    Default: 1"
                    ::= { endptSIP 236 }
									
endptSHAREDLINE9SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 237 }

endptSHAREDLINE10SIPUSERID  OBJECT-TYPE
                    SYNTAX      DisplayString (SIZE(0..255))
                    MAX-ACCESS  read-only
                    STATUS      current
                    DESCRIPTION "The AOR (Address of Record) for the shared line.
                    It should only specify the handle (e.g. 123456_2) since the domain is specified independently. 
                    Note that shared lines are only supported for the same SIP domain as the primary line.
                    The setting only applies to 3PCC server environments."
                    ::= { endptSIP 238 }

endptSHAREDLINE9USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA9_SIPUSERID would be used for authentication.
                    The setting only applies to 3PCC server environments."
                    ::= { endptSIP 239 }

endptSHAREDLINE10USERNAME  OBJECT-TYPE
                    SYNTAX      DisplayString (SIZE(0..255))
                    MAX-ACCESS  read-only
                    STATUS      current
                    DESCRIPTION "The username to be used for authentication when challenged for credentials on SIP requests 
                    associated with the shared line.
                    This value is optional and if not specified the SCA10_SIPUSERID would be used for authentication.
                    The setting only applies to 3PCC server environments."
                    ::= { endptSIP 240 }

endptSHAREDLINE9EXTENSION  OBJECT-TYPE
                    SYNTAX      DisplayString (SIZE(0..255))
                    MAX-ACCESS  read-only
                    STATUS      current
                    DESCRIPTION "The display name for the shared line. If not specified the SCA9_SIPUSERID would be used.
                    The setting only applies to 3PCC server environments."
                    ::= { endptSIP 241 }

endptSHAREDLINE10EXTENSION  OBJECT-TYPE
                    SYNTAX      DisplayString (SIZE(0..255))
                    MAX-ACCESS  read-only
                    STATUS      current
                    DESCRIPTION "The display name for the shared line. If not specified the SCA10_SIPUSERID would be used.
                    The setting only applies to 3PCC server environments."
                    ::= { endptSIP 242 }

endptSHAREDLINE9BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 243 }

endptSHAREDLINE10BARGEINENABLED  OBJECT-TYPE
                    SYNTAX      INTEGER
                    MAX-ACCESS  read-only
                    STATUS      current
                    DESCRIPTION "Each shared line can be configured in the Broadsoft server to either enable or disable the 
                    ability of a user to barge into a call at a different location on the shared line.
                    The setting only applies to 3PCC server environments.
                    Not used for BLA.
                    '0' Barge in is disabled for the shared line
                    '1' Barge in is enabled for the shared line (default)"
                    ::= { endptSIP 244 }

endptSHAREDLINE9INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 245 }

endptSHAREDLINE10INCOMINGCALLINDICATIONDEFAULT  OBJECT-TYPE
                    SYNTAX      INTEGER
                    MAX-ACCESS  read-only
                    STATUS      current
                    DESCRIPTION "Specifies how a Shared Call Appearance Line should behave when receiving an incoming call.
                    This parameter is applicable for SCA, BLA and BCA.
                    This is administrator part of the setting.
                    Indication Value can be:
                    0 - None
                    1 - Audible
                    2 - Visual
                    3 - Both (Default)
                    4 - None Forced
                    5 - Audible Forced
                    6 - Visual Forced
                    7 - Both Forced
                    Values <= 3 allow user to modify the setting in the User Menu.
                    This setting does not apply to a primary line which is shared."
                    ::= { endptSIP 246 }

endptSHAREDLINE9INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 247 }

endptSHAREDLINE10INCOMINGCALLINDICATIONDELAYEDDEFAULT  OBJECT-TYPE
                    SYNTAX      INTEGER
                    MAX-ACCESS  read-only
                    STATUS      current
                    DESCRIPTION "Specifies a value in seconds, used by the phone to delay the displaying of call popup
                    and playing of ringtone for an incoming call on a shared line which is not a primary line.
                    This parameter is applicable for SCA, BLA and BCA.
                    The parameter is only used when the corresponding Incoming Call Indication Mode is Audible or Visual or Both.
                    Indication Delay equal to 0 means no delay.
                    Users can override this value in the User Menu.
                    Range: 0-99
                    Default: 0"
                    ::= { endptSIP 248 }

endptSHAREDLINE9INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 249 }

endptSHAREDLINE10INCOMINGCALLINDICATION  OBJECT-TYPE
                    SYNTAX      INTEGER
                    MAX-ACCESS  read-only
                    STATUS      current
                    DESCRIPTION "Specifies how a Shared Call Appearance Line should behave when receiving an incoming call
                    This parameter is applicable for SCA, BLA and BCA.
                    This is user part of the setting.
                    Indication Value can be:
                    0 (Default) - Use value configured by the admin
                    1 - None
                    2 - Audible
                    3 - Visual
                    4 - Both
                    The value can be changes by the user if SCAn_INCOMING_CALL_INDICATION_DEFAULT <=3"
                    ::= { endptSIP 250 }

endptSHAREDLINE9INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 251 }

endptSHAREDLINE10INCOMINGCALLINDICATIONDELAYED  OBJECT-TYPE
                    SYNTAX      INTEGER
                    MAX-ACCESS  read-only
                    STATUS      current
                    DESCRIPTION "Specifies a value in seconds, used by the phone to delay the displaying of call popup  and playing of ringtone for an incoming call.
                    This parameter is user part of the setting and has a value configured by the user in the User Menu.
                    The parameter is only used when Incoming Call Indication Mode is Audible or Visual or Both.
                    Value equal to 0 means no delay.
                    Value equal to -1 means use SCA<n>_INCOMING_CALL_INDICATION_DELAYED_DEFAULT
                    Range: -1 - 99
                    Default: -1"
                    ::= { endptSIP 252 }

endptVVMVOICEMAILKEY  OBJECT-TYPE
                    SYNTAX      INTEGER
                    MAX-ACCESS  read-only
                    STATUS      current
                    DESCRIPTION "Defines the behavior of Voicemail (Envelope) button:
                    0 - (default) - Voicemail key is used according to the admin parameter VVM_VOICEMAIL_KEY_DEFAULT 
                    1 - Voicemail key is used to access Visual voicemail Inbox
                    2 - Voicemail key is used to dial IVR"
                    ::= { endptSIP 253 }

endptUSBPOWERLEVEL  OBJECT-TYPE
                    SYNTAX      INTEGER
                    MAX-ACCESS  read-only
                    STATUS      current
                    DESCRIPTION "Reflects the USB power level:
                    0 (default) - USB power not allowed
                    1 - Low USB power level
                    2 - Medium USB power level
                    3 - High USB power level"
                    ::= { endptSIP 254 }

endptEXCHANGEAUTHMETHODDEFAULT  OBJECT-TYPE
                    SYNTAX      INTEGER
                    MAX-ACCESS  read-only
                    STATUS      current
                    DESCRIPTION "Specifies the Exchange authentication method configured by Administrator:
                    0 (default) - Basic authentication
                    1 - OAuth
                    2 - Basic authentication - forced
                    3 - OAuth - forced
                    When admin configured method is Basic (Forced) or OAuth (Forced), it is the active authentication method. 
                    In this case phone user is not allowed to change the authentication method from phone user interface.
                    When admin configured method is non-forced, phone user can change the authentication method from phone user interface and 
					the active authentication method is going to be as configured by the phone user."
                    ::= { endptSIP 255 }

endptEXCHANGEUSERACCOUNTDEFAULT  OBJECT-TYPE
                    SYNTAX      DisplayString (SIZE(0..255))
                    MAX-ACCESS  read-only
                    STATUS      current
                    DESCRIPTION "Specifies the Exchange user account configured by Administrator. 
                    This parameter is only applicable when authentication method is OAuth.
                    If phone user hasn't configured any user name on the phone user interface
                    then value configured in this parameter would be used."
                    ::= { endptSIP 256 }

endptEXCHANGEEMAILDOMAINUSER  OBJECT-TYPE
                    SYNTAX      DisplayString (SIZE(0..255))
                    MAX-ACCESS  read-only
                    STATUS      current
                    DESCRIPTION "If the EXCHANGE_EMAIL_DOMAIN is not set in the settings file, 
                    it is up to the user to enter the domain part of their email address. 
                    So if this setting is not empty because it has been entered by the user, 
                    it will be used to construct the user's email address."
                    ::= { endptSIP 257 }

endptEXCHANGESERVERLISTUSER  OBJECT-TYPE
                    SYNTAX      DisplayString (SIZE(0..255))
                    MAX-ACCESS  read-only
                    STATUS      current
                    DESCRIPTION "If the EXCHANGE_SERVER_LIST is not set in the settings file (i.e. it is empty), 
                    it is up to the user to enter the server's host address (as an FQDN)"
                    ::= { endptSIP 258 }

endptEXCHANGEAUTHMETHOD  OBJECT-TYPE
                    SYNTAX      INTEGER
                    MAX-ACCESS  read-only
                    STATUS      current
                    DESCRIPTION "If the EXCHANGE_AUTH_METHOD_DEFAULT is not set in the settings file then
                    the user needs to be able to manually set the value from phone UI.
                    Range: 0-2
                    Default: 0"
                    ::= { endptSIP 259 }

endptSOFTKEYSCATRANSFERDIALING  OBJECT-TYPE
                    SYNTAX      DisplayString
                    MAX-ACCESS  read-only
                    STATUS      current
                    DESCRIPTION "Describes new custom softkey for SCA/BLA/BCA lines in TRANSFER DIALING state."
                    ::= { endptSIP 260 }

endptOVERRIDESOFTKEYSCATRANSFERDIALING  OBJECT-TYPE
                    SYNTAX      INTEGER
                    MAX-ACCESS  read-only
                    STATUS      current
                    DESCRIPTION "Determines if default softkeys will be shown for SCA/BLA/BCA lines in TRANSFER DIALING state.
                    0 (Default) - default softkeys will be shown.
                    1 - default softkeys will NOT be shown."
                    ::= { endptSIP 261 }

endptSOFTKEYSCATRANSFEROUTGOING  OBJECT-TYPE
                    SYNTAX      DisplayString
                    MAX-ACCESS  read-only
                    STATUS      current
                    DESCRIPTION "Describes new custom softkey for SCA/BLA/BCA lines in TRANSFER OUTGOING state."
                    ::= { endptSIP 262 }

endptOVERRIDESOFTKEYSCATRANSFEROUTGOING  OBJECT-TYPE
                    SYNTAX      INTEGER
                    MAX-ACCESS  read-only
                    STATUS      current
                    DESCRIPTION "Determines if default softkeys will be shown for SCA/BLA/BCA lines in TRANSFER OUTGOING state.
                    0 (Default) - default softkeys will be shown.
                    1 - default softkeys will NOT be shown."
                    ::= { endptSIP 263 }

endptSOFTKEYSCATRANSFERCONSULT  OBJECT-TYPE
                    SYNTAX      DisplayString
                    MAX-ACCESS  read-only
                    STATUS      current
                    DESCRIPTION "Describes new custom softkey for SCA/BLA/BCA lines in TRANSFER CONSULT state."
                    ::= { endptSIP 264 }

endptOVERRIDESOFTKEYSCATRANSFERCONSULT  OBJECT-TYPE
                    SYNTAX      INTEGER
                    MAX-ACCESS  read-only
                    STATUS      current
                    DESCRIPTION "Determines if default softkeys will be shown for SCA/BLA/BCA lines in TRANSFER CONSULT state.
                    0 (Default) - default softkeys will be shown.
                    1 - default softkeys will NOT be shown."
                    ::= { endptSIP 265 }

endptSOFTKEYSCADIALING  OBJECT-TYPE
                    SYNTAX      DisplayString
                    MAX-ACCESS  read-only
                    STATUS      current
                    DESCRIPTION "Describes new custom softkey for SCA/BLA/BCA lines in DIALING state."
                    ::= { endptSIP 266 }

endptOVERRIDESOFTKEYSCADIALING  OBJECT-TYPE
                    SYNTAX      INTEGER
                    MAX-ACCESS  read-only
                    STATUS      current
                    DESCRIPTION "Determines if default softkeys will be shown for SCA/BLA/BCA lines in DIALING state.
                    0 (Default) - default softkeys will be shown.
                    1 - default softkeys will NOT be shown."
                    ::= { endptSIP 267 }

endptSOFTKEYSCADIALTONE  OBJECT-TYPE
                    SYNTAX      DisplayString
                    MAX-ACCESS  read-only
                    STATUS      current
                    DESCRIPTION "Describes new custom softkey for SCA/BLA/BCA lines in DIALTONE state."
                    ::= { endptSIP 268 }

endptOVERRIDESOFTKEYSCADIALTONE  OBJECT-TYPE
                    SYNTAX      INTEGER
                    MAX-ACCESS  read-only
                    STATUS      current
                    DESCRIPTION "Determines if default softkeys will be shown for SCA/BLA/BCA lines in DIALTONE state.
                    0 (Default) - default softkeys will be shown.
                    1 - default softkeys will NOT be shown."
                    ::= { endptSIP 269 }

endptSOFTKEYDIALING  OBJECT-TYPE
                    SYNTAX      DisplayString
                    MAX-ACCESS  read-only
                    STATUS      current
                    DESCRIPTION "Describes new custom softkey for Primary CA lines in DIALING state."
                    ::= { endptSIP 270 }

endptOVERRIDESOFTKEYDIALING  OBJECT-TYPE
                    SYNTAX      INTEGER
                    MAX-ACCESS  read-only
                    STATUS      current
                    DESCRIPTION "Determines if default softkeys will be shown for Primary CA lines in DIALING state.
                    0 (Default) - default softkeys will be shown.
                    1 - default softkeys will NOT be shown."
                    ::= { endptSIP 271 }

endptSOFTKEYDIALTONE  OBJECT-TYPE
                    SYNTAX      DisplayString
                    MAX-ACCESS  read-only
                    STATUS      current
                    DESCRIPTION "Describes new custom softkey for Primary CA lines in DIALTONE state."
                    ::= { endptSIP 272 }

endptOVERRIDESOFTKEYDIALTONE  OBJECT-TYPE
                    SYNTAX      INTEGER
                    MAX-ACCESS  read-only
                    STATUS      current
                    DESCRIPTION "Determines if default softkeys will be shown for Primary CA lines in DIALTONE state.
                    0 (Default) - default softkeys will be shown.
                    1 - default softkeys will NOT be shown."
                    ::= { endptSIP 273 }

endptSOFTKEYTRANSFERDIALING  OBJECT-TYPE
                    SYNTAX      DisplayString
                    MAX-ACCESS  read-only
                    STATUS      current
                    DESCRIPTION "Describes new custom softkey for Primary CA lines in TRANSFER DIALING state."
                    ::= { endptSIP 274 }

endptOVERRIDESOFTKEYTRANSFERDIALING  OBJECT-TYPE
                    SYNTAX      INTEGER
                    MAX-ACCESS  read-only
                    STATUS      current
                    DESCRIPTION "Determines if default softkeys will be shown for Primary CA lines in TRANSFER DIALING state.
                    0 (Default) - default softkeys will be shown.
                    1 - default softkeys will NOT be shown."
                    ::= { endptSIP 275 }

endptSOFTKEYTRANSFEROUTGOING  OBJECT-TYPE
                    SYNTAX      DisplayString
                    MAX-ACCESS  read-only
                    STATUS      current
                    DESCRIPTION "Describes new custom softkey for Primary CA lines in TRANSFER OUTGOING state."
                    ::= { endptSIP 276 }

endptOVERRIDESOFTKEYTRANSFEROUTGOING  OBJECT-TYPE
                    SYNTAX      INTEGER
                    MAX-ACCESS  read-only
                    STATUS      current
                    DESCRIPTION "Determines if default softkeys will be shown for Primary CA lines in TRANSFER OUTGOING state.
                    0 (Default) - default softkeys will be shown.
                    1 - default softkeys will NOT be shown."
                    ::= { endptSIP 277 }

endptSOFTKEYTRANSFERCONSULT  OBJECT-TYPE
                    SYNTAX      DisplayString
                    MAX-ACCESS  read-only
                    STATUS      current
                    DESCRIPTION "Describes new custom softkey for Primary CA lines in TRANSFER CONSULT state."
                    ::= { endptSIP 278 }

endptOVERRIDESOFTKEYTRANSFERCONSULT  OBJECT-TYPE
                    SYNTAX      INTEGER
                    MAX-ACCESS  read-only
                    STATUS      current
                    DESCRIPTION "Determines if default softkeys will be shown for Primary CA lines in TRANSFER CONSULT state.
                    0 (Default) - default softkeys will be shown.
                    1 - default softkeys will NOT be shown."
                    ::= { endptSIP 279 }

endptSOFTKEYSCAREMOTEACTIVE  OBJECT-TYPE
                    SYNTAX      DisplayString
                    MAX-ACCESS  read-only
                    STATUS      current
                    DESCRIPTION "Describes new custom softkey for SCA/BLA/BCA lines in REMOTE ACTIVE state."
                    ::= { endptSIP 280 }

endptOVERRIDESOFTKEYSCAREMOTEACTIVE  OBJECT-TYPE
                    SYNTAX      INTEGER
                    MAX-ACCESS  read-only
                    STATUS      current
                    DESCRIPTION "Determines if default softkeys will be shown for SCA/BLA/BCA lines in REMOTE ACTIVE state.
                    0 (Default) - default softkeys will be shown.
                    1 - default softkeys will NOT be shown."
                    ::= { endptSIP 281 }

endptSOFTKEYSCAREMOTEHELD  OBJECT-TYPE
                    SYNTAX      DisplayString
                    MAX-ACCESS  read-only
                    STATUS      current
                    DESCRIPTION "Describes new custom softkey for SCA/BLA/BCA lines in REMOTE HELD state."
                    ::= { endptSIP 282 }

endptOVERRIDESOFTKEYSCAREMOTEHELD  OBJECT-TYPE
                    SYNTAX      INTEGER
                    MAX-ACCESS  read-only
                    STATUS      current
                    DESCRIPTION "Determines if default softkeys will be shown for SCA/BLA/BCA lines in REMOTE HELD state.
                    0 (Default) - default softkeys will be shown.
                    1 - default softkeys will NOT be shown."
                    ::= { endptSIP 283 }

endptUSBHEADSETMODEL  OBJECT-TYPE
                    SYNTAX      DisplayString
                    MAX-ACCESS  read-only
                    STATUS      current
                    DESCRIPTION "Reflects connected headset model."
                    ::= { endptSIP 284 }

endptUSBHEADSETMANUFACTURER  OBJECT-TYPE
                    SYNTAX      DisplayString
                    MAX-ACCESS  read-only
                    STATUS      current
                    DESCRIPTION "Reflects connected headset manufacture."
                    ::= { endptSIP 285 }

endptUSBHEADSETSN  OBJECT-TYPE
                    SYNTAX      DisplayString
                    MAX-ACCESS  read-only
                    STATUS      current
                    DESCRIPTION "Reflects connected headset serial number."
                    ::= { endptSIP 286 }

endptUSBHEADSETFW  OBJECT-TYPE
                    SYNTAX      DisplayString
                    MAX-ACCESS  read-only
                    STATUS      current
                    DESCRIPTION "Reflects connected headset firmware version."
                    ::= { endptSIP 287 }

endptBLFLISTPREFERREDSTARTLOCATION  OBJECT-TYPE
                    SYNTAX      INTEGER
                    MAX-ACCESS  read-only
                    STATUS      current
                    DESCRIPTION "This parameter controls where detected BLFs would be placed on the home screen. 
                    BLFs are detected from BLF List URI. It provides the starting location from which the detected BLFs will be placed.
                    0 = BLFs will be placed depending on Button Module detection. Starting location is 1 if no BM. 
                     Starting location is 25 if a button module detected on the phone.
                    N (1 - 96) = For example, if BLFs are to be placed starting from line key location 1 then N should be 1.
                    Range: 0-96
                    Default: 0"
                    ::= { endptSIP 288 }

endptBLFLISTLINEKEYLOCATIONFORCED  OBJECT-TYPE
                    SYNTAX      INTEGER
                    MAX-ACCESS  read-only
                    STATUS      current
                    DESCRIPTION "This parameter sets 'forced' property of a BLF line key detected from BLF LIST URI. When 'forced' BLF line key can not be moved.
                    0 - unforced
                    1 (Default) - forced (user cannot move the BLF list line keys)
                    Recommended value for this parameter should be 1. This would make the detected BLFs to be not moved."
                    ::= { endptSIP 289 }

endptAUTOMATICUPDATEPOLICY  OBJECT-TYPE
                    SYNTAX      INTEGER
                    MAX-ACCESS  read-only
                    STATUS      current
                    DESCRIPTION "This parameter give control to change automatic update policy mode.
                    Value Policy Mode:
                    0 - disabled (default)
                    1 - daily
                    2 - weekly
                    3 - monthly"
                    ::= { endptSIP 290 }

endptAUTOMATICUPDATEDAYS  OBJECT-TYPE
                    SYNTAX      DisplayString
                    MAX-ACCESS  read-only
                    STATUS      current
                    DESCRIPTION "Mon,Tue,Wed,Thu,Fri,Sat,Sun (for Weekly)
                    xMon,xTue,xWed,xThu,xFri,xSat,xSun (for Monthly) where x = which occurrence of the month. i.e. 2Sat = 2nd Saturday of the Month.
                    Default: Sun (for weekly, this means Sunday, for monthly, this would map to 1Sun, i.e. 1st Sunday of the Month)
                    Ignored if AUTOMATIC_UPDATE_POLICY set to 0 or 1.
                    If policy is weekly and user configured days as '3Mon,3Tue,3Wed,4Thu,4Fri,4Sat,4Sun', then phone should use default value i.e. 'Sun'
                    i.e. if invalid configuration detected then phone will use default value.
                    Note: Administrator can define multiples via comma separated"
                    ::= { endptSIP 291 }

endptAUTOMATICUPDATEWINDOW  OBJECT-TYPE
                    SYNTAX      DisplayString
                    MAX-ACCESS  read-only
                    STATUS      current
                    DESCRIPTION "m,n - specifies hours of a day (in 24h format) for Begin and End of the window automatic settings/firmware update is allowed.
                    Each phone will choose random start time in this window
                    E.g. 3,4 - means the settings/firmware update will begin between 3AM and 4AM
                    Default: 2,4
                    e.g.
                    - 3,3 will consider as 24 hr valid range.
                    - 12,25 is invalid range and phone will use default range i.e. 2,4
                    12,4 is valid 16hr range. (i.e. 12 - 24 & 1 - 4)"
                    ::= { endptSIP 292 }

endptAUTOMATICUPGRADEINSTALLDATETIME  OBJECT-TYPE
                    SYNTAX      DisplayString
                    MAX-ACCESS  read-only
                    STATUS      current
                    DESCRIPTION "Specifies The date and time after which new firmware will be downloaded and installed.
                    Once this date and time is reached, J100 will follow AUTOMATIC_UPDATE_DAYS and AUTOMATIC_UPDATE_WINDOW to trigger the reboot for firmware download.
                    Default value is NULL. So when this parameter is not set, phone will follow AUTOMATIC_UPDATE_POLICY, AUTOMATIC_UPDATE_DAYS and AUTOMATIC_UPDATE_WINDOW to trigger the firmware download.
                    Note: UPGRADE_INSTALL_DATE_TIME is applicable when AUTOMATIC_UPDATE_POLICY is 1, 2 or 3.
                    The format is YYYY-MM-DDThh:mm, where YYYY is a 4 numeric digits representing the year, MM is 2 numeric digits for month 01-12,
                    dd is two numeric digits representing the day of the month, from 01 through 31, 'T' stand for Time separator,
                    hh is two numeric digits representing the hour of the day, from 00 through 23 and mm is two numeric digits representing minutes of the hour,
                    from 00 through 59. The default is NULL.
                    Note: This parameter applies to the phones local time as defined by based on GMTOFFSET, DAYLIGHT_SAVING_SETTING_MODE, DSTOFFSET, DSTSTART and DSTSTOP.
                    Example: SET UPGRADE_INSTALL_DATE_TIME 2015-04-12T23:20"
                    ::= { endptSIP 293 }

endptAUTOMATICUPDATEREBOOTPROMPT  OBJECT-TYPE
                    SYNTAX      INTEGER
                    MAX-ACCESS  read-only
                    STATUS      current
                    DESCRIPTION "Phone has detected new settings requiring a reboot.
                    1, reboot confirmation prompt will be shown on phone UI
                    0, reboot confirmation prompt will not be shown on phone UI, i.e. phone directly do the upgrade instead of confirmation from user.
                    Default value is 0.
                    This prompt is for firmware upgrade only.
                    Note: If reboot action parameter is changed & phone is idle then phone will ALWAYS reboot."
                    ::= { endptSIP 294 }

endptLOGSRVRSECURE  OBJECT-TYPE
                    SYNTAX      INTEGER
                    MAX-ACCESS  read-only
                    STATUS      current
                    DESCRIPTION "Defines if secure or non-secure syslog is to be used by default.
                    0 (Default) - Non-secure using UDP transport (existing behavior)
                    1 - Secure syslog using TLS transport using RFC 5425
                    Selected value wiil be available as Default option in admin menu"
                    ::= { endptSIP 295 }

endptPUSHMODE  OBJECT-TYPE
                    SYNTAX      INTEGER
                    MAX-ACCESS  read-only
                    STATUS      current
                    DESCRIPTION "Specifies which combination of non-secure and secure push is to be used.
                    0 - Only non-secure Push (http) is enabled
                    1 - Only secure Push (https) is enabled
                    2 (Default) - Both secure and non-secure Push are enabled
                    NOTE: If there is no identity certificate installed on the phone with the serverAuth attribute, then only http can be used. 
                    This means that if PUSH_MODE = 1, Push will be disabled and if PUSH_MODE=2 then only non-secure will be used. 
                    In this last case, the Subscribe Push must indicate 'nonsecure'."
                    ::= { endptSIP 296 }

endptPUSHPORTSECURE  OBJECT-TYPE
                    SYNTAX      INTEGER
                    MAX-ACCESS  read-only
                    STATUS      current
                    DESCRIPTION "Specifies the port to be used to listen for incoming secure Push requests over https if secure push is enabled.
                    NOTE: The default value is set to 8443 to avoid a conflict with the web server in the phone using the default value."
                    ::= { endptSIP 297 }

endptPHONEKEYLISTENHANCED  OBJECT-TYPE
                    SYNTAX      DisplayString
                    MAX-ACCESS  read-only
                    STATUS      current
                    DESCRIPTION "This parameter is a concatenation of PHONEKEY parameter in 46xxSettings file. Each PHONEKEY entry is separated by ';;'"
                    ::= { endptSIP 298 }

endptNEXTAUTOMATICUPDATEINTERVAL  OBJECT-TYPE
                    SYNTAX      DisplayString
                    MAX-ACCESS  read-only
                    STATUS      current
                    DESCRIPTION "Next automatic update time"
                    ::= { endptSIP 299 }

endptLASTUPDATE  OBJECT-TYPE
                    SYNTAX      DisplayString
                    MAX-ACCESS  read-only
                    STATUS      current
                    DESCRIPTION "Last update time"
                    ::= { endptSIP 300 }

endptUSBSTICKMODEL  OBJECT-TYPE
                    SYNTAX      DisplayString
                    MAX-ACCESS  read-only
                    STATUS      current
                    DESCRIPTION "Reflects connected stick model."
                    ::= { endptSIP 301 }

endptUSBSTICKMANUFACTURER  OBJECT-TYPE
                    SYNTAX      DisplayString
                    MAX-ACCESS  read-only
                    STATUS      current
                    DESCRIPTION "Reflects connected stick manufacture."
                    ::= { endptSIP 302 }

endptUSBSTICKSN  OBJECT-TYPE
                    SYNTAX      DisplayString
                    MAX-ACCESS  read-only
                    STATUS      current
                    DESCRIPTION "Reflects connected stick serial number."
                    ::= { endptSIP 303 }

endptUSBSTICKFW  OBJECT-TYPE
                    SYNTAX      DisplayString
                    MAX-ACCESS  read-only
                    STATUS      current
                    DESCRIPTION "Reflects connected stick firmware version."
                    ::= { endptSIP 304 }

endptUSBKEYBOARDMODEL  OBJECT-TYPE
                    SYNTAX      DisplayString
                    MAX-ACCESS  read-only
                    STATUS      current
                    DESCRIPTION "Reflects connected keyboard model."
                    ::= { endptSIP 305 }

endptUSBKEYBOARDMANUFACTURER  OBJECT-TYPE
                    SYNTAX      DisplayString
                    MAX-ACCESS  read-only
                    STATUS      current
                    DESCRIPTION "Reflects connected keyboard manufacture."
                    ::= { endptSIP 306 }

endptUSBKEYBOARDSN  OBJECT-TYPE
                    SYNTAX      DisplayString
                    MAX-ACCESS  read-only
                    STATUS      current
                    DESCRIPTION "Reflects connected keyboard serial number."
                    ::= { endptSIP 307 }

endptUSBKEYBOARDFW  OBJECT-TYPE
                    SYNTAX      DisplayString
                    MAX-ACCESS  read-only
                    STATUS      current
                    DESCRIPTION "Reflects connected keyboard firmware version."
                    ::= { endptSIP 308 }

endptENABLEUSBDEVICE  OBJECT-TYPE
                    SYNTAX      INTEGER
                    MAX-ACCESS  read-only
                    STATUS      current
                    DESCRIPTION "Enable/disable support of USB devices on the phone.
                    Range: 0 - 1
                    Default: 1"
                    ::= { endptSIP 309 }

endptENABLEUSBSTICK  OBJECT-TYPE
                    SYNTAX      INTEGER
                    MAX-ACCESS  read-only
                    STATUS      current
                    DESCRIPTION "Enable or disable USB Flash Drive support.
                    Range: 0 - 1
                    Default: 1"
                    ::= { endptSIP 310 }

endptENABLEUSBKEYBOARD  OBJECT-TYPE
                    SYNTAX      INTEGER
                    MAX-ACCESS  read-only
                    STATUS      current
                    DESCRIPTION "Enable or disable USB Keyboard support.
                    Range: 0 - 1
                    Default: 1"
                    ::= { endptSIP 311 }

endptSHAREDLINE1SUBSCRIBETARGET  OBJECT-TYPE
                    SYNTAX      DisplayString
                    MAX-ACCESS  read-only
                    STATUS      current
                    DESCRIPTION "The AOR (Address of Record) of the subscription target for the shared line.
                    If it is empty (not set), the subscription target is set to SCA1_SIPUSERID
                    i.e. subscription and registration targets are identical.
                    It should only specify the handle (e.g. 123456_2) since the domain is specified independently.
                    Note that shared lines are only supported for the same SIP domain as the primary line."
                    ::= { endptSIP 312 }

endptSHAREDLINE2SUBSCRIBETARGET  OBJECT-TYPE
                    SYNTAX      DisplayString
                    MAX-ACCESS  read-only
                    STATUS      current
                    DESCRIPTION "The AOR (Address of Record) of the subscription target for the shared line.
                    If it is empty (not set), the subscription target is set to SCA2_SIPUSERID
                    i.e. subscription and registration targets are identical.
                    It should only specify the handle (e.g. 123456_2) since the domain is specified independently.
                    Note that shared lines are only supported for the same SIP domain as the primary line."
                    ::= { endptSIP 313 }

endptSHAREDLINE3SUBSCRIBETARGET  OBJECT-TYPE
                    SYNTAX      DisplayString
                    MAX-ACCESS  read-only
                    STATUS      current
                    DESCRIPTION "The AOR (Address of Record) of the subscription target for the shared line.
                    If it is empty (not set), the subscription target is set to SCA3_SIPUSERID
                    i.e. subscription and registration targets are identical.
                    It should only specify the handle (e.g. 123456_2) since the domain is specified independently.
                    Note that shared lines are only supported for the same SIP domain as the primary line."
                    ::= { endptSIP 314 }

endptSHAREDLINE4SUBSCRIBETARGET  OBJECT-TYPE
                    SYNTAX      DisplayString
                    MAX-ACCESS  read-only
                    STATUS      current
                    DESCRIPTION "The AOR (Address of Record) of the subscription target for the shared line.
                    If it is empty (not set), the subscription target is set to SCA4_SIPUSERID
                    i.e. subscription and registration targets are identical.
                    It should only specify the handle (e.g. 123456_2) since the domain is specified independently.
                    Note that shared lines are only supported for the same SIP domain as the primary line."
                    ::= { endptSIP 315 }

endptSHAREDLINE5SUBSCRIBETARGET  OBJECT-TYPE
                    SYNTAX      DisplayString
                    MAX-ACCESS  read-only
                    STATUS      current
                    DESCRIPTION "The AOR (Address of Record) of the subscription target for the shared line.
                    If it is empty (not set), the subscription target is set to SCA5_SIPUSERID
                    i.e. subscription and registration targets are identical.
                    It should only specify the handle (e.g. 123456_2) since the domain is specified independently.
                    Note that shared lines are only supported for the same SIP domain as the primary line."
                    ::= { endptSIP 316 }

endptSHAREDLINE6SUBSCRIBETARGET  OBJECT-TYPE
                    SYNTAX      DisplayString
                    MAX-ACCESS  read-only
                    STATUS      current
                    DESCRIPTION "The AOR (Address of Record) of the subscription target for the shared line.
                    If it is empty (not set), the subscription target is set to SCA6_SIPUSERID
                    i.e. subscription and registration targets are identical.
                    It should only specify the handle (e.g. 123456_2) since the domain is specified independently.
                    Note that shared lines are only supported for the same SIP domain as the primary line."
                    ::= { endptSIP 317 }

endptSHAREDLINE7SUBSCRIBETARGET  OBJECT-TYPE
                    SYNTAX      DisplayString
                    MAX-ACCESS  read-only
                    STATUS      current
                    DESCRIPTION "The AOR (Address of Record) of the subscription target for the shared line.
                    If it is empty (not set), the subscription target is set to SCA7_SIPUSERID
                    i.e. subscription and registration targets are identical.
                    It should only specify the handle (e.g. 123456_2) since the domain is specified independently.
                    Note that shared lines are only supported for the same SIP domain as the primary line."
                    ::= { endptSIP 318 }

endptSHAREDLINE8SUBSCRIBETARGET  OBJECT-TYPE
                    SYNTAX      DisplayString
                    MAX-ACCESS  read-only
                    STATUS      current
                    DESCRIPTION "The AOR (Address of Record) of the subscription target for the shared line.
                    If it is empty (not set), the subscription target is set to SCA8_SIPUSERID
                    i.e. subscription and registration targets are identical.
                    It should only specify the handle (e.g. 123456_2) since the domain is specified independently.
                    Note that shared lines are only supported for the same SIP domain as the primary line."
                    ::= { endptSIP 319 }

endptSHAREDLINE9SUBSCRIBETARGET  OBJECT-TYPE
                    SYNTAX      DisplayString
                    MAX-ACCESS  read-only
                    STATUS      current
                    DESCRIPTION "The AOR (Address of Record) of the subscription target for the shared line.
                    If it is empty (not set), the subscription target is set to SCA9_SIPUSERID
                    i.e. subscription and registration targets are identical.
                    It should only specify the handle (e.g. 123456_2) since the domain is specified independently.
                    Note that shared lines are only supported for the same SIP domain as the primary line."
                    ::= { endptSIP 320 }
                    
endptSHAREDLINE10SUBSCRIBETARGET  OBJECT-TYPE
                    SYNTAX      DisplayString
                    MAX-ACCESS  read-only
                    STATUS      current
                    DESCRIPTION "The AOR (Address of Record) of the subscription target for the shared line.
                    If it is empty (not set), the subscription target is set to SCA10_SIPUSERID
                    i.e. subscription and registration targets are identical.
                    It should only specify the handle (e.g. 123456_2) since the domain is specified independently.
                    Note that shared lines are only supported for the same SIP domain as the primary line."
                    ::= { endptSIP 321 }

endptWIFI   OBJECT IDENTIFIER ::= { avayaSparkMIB 8 }
endptWIFISTAT   OBJECT-TYPE
                    SYNTAX      INTEGER
                    MAX-ACCESS  read-only
                    STATUS      current
                    DESCRIPTION "Wi-Fi Mode of operation. This variable returns values: 
                    '0' Wi-Fi Disabled, 
                    '1' Wi-Fi Unrestricted or Ethernet (default), 
                    '2' Wi-Fi Restricted or Ethernet, 
                    '3' Wi-Fi Only, Unrestricted,
                    '4' Wi-Fi Only"
                    ::= { endptWIFI 1 }
endptWIFIIPADD  OBJECT-TYPE
                    SYNTAX      IpAddress
                    MAX-ACCESS  read-only
                    STATUS      current
                    DESCRIPTION "Endpoint IP address on Wi-Fi. This variable returns a 
                    4-octet string specifying the endpoint's current IP address:
                    If DHCP off: Statically-configured phone IP address, 
                    If DHCP on: Value of WIFIIPADD obtained via DHCP"
                    ::= { endptWIFI 2 }
endptWIFIGIPADD  OBJECT-TYPE
                    SYNTAX      IpAddress
                    MAX-ACCESS  read-only
                    STATUS      current
                    DESCRIPTION "Gateway/router IP address on Wi-Fi. This variable returns a 
                    4-octet string specifying the current gateway/router IP address:
                    If DHCP off: Statically-configured gateway/router IP address, 
                    If DHCP on: Value of WIFIGIPADD obtained via DHCP"
                    ::= { endptWIFI 3 }
endptWIFINETMASK    OBJECT-TYPE
                    SYNTAX      IpAddress
                    MAX-ACCESS  read-only
                    STATUS      current
                    DESCRIPTION "Subnet mask on Wi-Fi. This variable returns a  
                    4-octet string specifying the subnet mask currently in use:
                    If DHCP off: Statically-configured network mask,
                    If DHCP on: Value of WIFINETMASK obtained via DHCP"
                    ::= { endptWIFI 4 }
endptWLANESSID OBJECT-TYPE
                    SYNTAX      DisplayString
                    MAX-ACCESS  read-only
                    STATUS      current
                    DESCRIPTION "SSID of WLAN network to be used.(configured from 46xxsettings.txt). 
                    String of up to 32 characters"
                    ::= { endptWIFI 5 }
endptWLANSECURITY  OBJECT-TYPE
                    SYNTAX      DisplayString
                    MAX-ACCESS  read-only
                    STATUS      current
                    DESCRIPTION "WLAN Security Standard used: 
                    'none' for no security, 
                    'wep' for WEP security, 
                    'wpa2psk' for WPA2 security with pre-shared key, 
                    'wpapsk' for WPA security wit pre-shared key,  
                    'wpa2e' for WPA2 Enterprise security (802.1x auth.)"
                    ::= { endptWIFI 6 }
endptWEPAUTHENTICATION  OBJECT-TYPE
                    SYNTAX      DisplayString
                    MAX-ACCESS  read-only
                    STATUS      current
                    DESCRIPTION "WEP authentication used: 
                    'openSystem' for WEP open systems, 
                    'sharedKey' for WEP with shared key authentication"
                    ::= { endptWIFI 7 }
--endptWEPDEFAULTKEY   OBJECT-TYPE
--                    SYNTAX      INTEGER
--                    MAX-ACCESS  read-only
--                    STATUS      current
--                    DESCRIPTION "Index of WEP default key. The range is 1 to 4"
--                    ::= { endptWIFI 8 }
endptWEPKEYLEN  OBJECT-TYPE
                    SYNTAX      DisplayString
                    MAX-ACCESS  read-only
                    STATUS      current
                    DESCRIPTION "Length of WEP key: 
                    '40bit' for WEP keys of 40 bits, 
                    '128bit' for WEP keys of 128 bits"
                    ::= { endptWIFI 9 }
--endptWEPKEY1   OBJECT-TYPE
--                    SYNTAX      DisplayString
--                    MAX-ACCESS  read-only
--                    STATUS      current
--                    DESCRIPTION "WEP Keys 1 from the range 1..4.
--                    Default not set, is an empty string. 
--                    Format is 10 hex digits for 40 bit keys, 26 hex digits for 128 bit keys"
--                    ::= { endptWIFI 10 }
--endptWEPKEY2   OBJECT-TYPE
--                    SYNTAX      DisplayString
--                    MAX-ACCESS  read-only
--                    STATUS      current
--                    DESCRIPTION "WEP Keys 2 from the range 1..4.
--                    Default not set, is an empty string. 
--                    Format is 10 hex digits for 40 bit keys, 26 hex digits for 128 bit keys"
--                    ::= { endptWIFI 11 }
--endptWEPKEY3   OBJECT-TYPE
--                    SYNTAX      DisplayString
--                    MAX-ACCESS  read-only
--                    STATUS      current
--                    DESCRIPTION "WEP Keys 3 from the range 1..4.
--                    Default not set, is an empty string. 
--                    Format is 10 hex digits for 40 bit keys, 26 hex digits for 128 bit keys"
--                    ::= { endptWIFI 12 }
--endptWEPKEY4   OBJECT-TYPE
--                    SYNTAX      DisplayString
--                    MAX-ACCESS  read-only
--                    STATUS      current
--                    DESCRIPTION "WEP Keys 4 from the range 1..4.
--                    Default not set, is an empty string. 
--                    Format is 10 hex digits for 40 bit keys, 26 hex digits for 128 bit keys"
--                    ::= { endptWIFI 13 }
--endptWLANPASSWORD  OBJECT-TYPE
--                    SYNTAX      DisplayString
--                    MAX-ACCESS  read-only
--                    STATUS      current
--                    DESCRIPTION "Preconfigured Wi-Fi Network Password. 
--                    This parameter is applicable if WIFISTAT enables Wi-Fi. This can be from 1-64 characters. 
--                    Valid characters are A-Z, a-z, 0-9, space, and some other special symbols. 
--                    Empty value is used to erase any previously set value"
--                    ::= { endptWIFI 15 }
endptWLANWPA2EEAPMETHOD  OBJECT-TYPE
                    SYNTAX      DisplayString
                    MAX-ACCESS  read-only
                    STATUS      current
                    DESCRIPTION "Pre-configured WPA2 EAP Method for 802.1x authentication of Wi-Fi network. 
                    This parameter is applicable if WIFISTAT enables Wi-Fi. 
                    Can be set to: 'PEAP' (Default), 'TLS', 'TTLS', 'PWD'"
                    ::= { endptWIFI 16 }
endptWLANWPA2EEAPPHASE2  OBJECT-TYPE
                    SYNTAX      DisplayString
                    MAX-ACCESS  read-only
                    STATUS      current
                    DESCRIPTION "Pre-configured WPA2 EAP Phase 2 Method for 802.1x authentication of Wi-Fi network. 
                    This parameter is applicable if WIFISTAT enables Wi-Fi. 
                    Can be set to 'none' (Default), 'MSCHAPV2', 'GTC'"
                    ::= { endptWIFI 17 }
endptWLANWPA2EIDENTITY   OBJECT-TYPE
                    SYNTAX      DisplayString
                    MAX-ACCESS  read-only
                    STATUS      current
                    DESCRIPTION "Pre-configured Identity for 802.1x authentication of Wi-Fi network. 
                    This parameter is applicable if WIFISTAT enables Wi-Fi. 
                    1-32 ASCII characters. Default is empty."
                    ::= { endptWIFI 18 }
endptWLANWPA2EANONYMOUSIDENTITY   OBJECT-TYPE
                    SYNTAX      DisplayString
                    MAX-ACCESS  read-only
                    STATUS      current
                    DESCRIPTION "Pre-configured anonymous identity for 802.1x authentication of Wi-Fi network. 
                    This parameter is applicable if WIFISTAT enables Wi-Fi. 
                    1-32 ASCII characters. Default is empty."
                    ::= { endptWIFI 19 }
endptACTIVENETWORK  OBJECT-TYPE
                    SYNTAX      INTEGER
                    MAX-ACCESS  read-only
                    STATUS      current
                    DESCRIPTION "Network interface that was actually activated during application initialization.
                    Used to remember the active interface when the phone is rebooted.
                    '1' for Ethernet, '2' for Ethernet and Wi-Fi (Future Rel.2), '3' for Wi-Fi"
                    ::= { endptWIFI 20 }
endptWLANACTIVESIGNALSTRENGTH   OBJECT-TYPE
                    SYNTAX      INTEGER
                    MAX-ACCESS  read-only
                    STATUS      current
                    DESCRIPTION "This variable returns value for current Wi-Fi AP signal strength.
                    Range is 0-4, with a default of 0"
                    ::= { endptWIFI 21 }
endptWLANACTIVESSID OBJECT-TYPE
                    SYNTAX      DisplayString
                    MAX-ACCESS  read-only
                    STATUS      current
                    DESCRIPTION "Active SSID. If this parameter is empty or has a value that is not in WLANLIST, 
                    then it will be assigned the value of 46xxsettings.txt WLAN_ESSID (which still could be empty). 
                    String of up to 32 characters"
                    ::= { endptWIFI 22 }
endptDOWIFIDHCPV4   OBJECT-TYPE
                    SYNTAX      INTEGER
                    MAX-ACCESS  read-only
                    STATUS      current
                    DESCRIPTION "DHCP mode for Wi-Fi. This variable returns 0 if IP 
                    address for Wi-Fi is a static configuration, or 1 
                    if a dynamic IP address is received via DHCP over the Wi-Fi."
                    ::= { endptWIFI 23 }
endptWlanListSize   OBJECT-TYPE
                    SYNTAX      INTEGER
                    MAX-ACCESS  read-only
                    STATUS      current
                    DESCRIPTION "Number of Wi-Fi networks that have been 
            previously connected"
                    ::= { endptWIFI 24 }
endptWlanListTable  OBJECT-TYPE
                SYNTAX SEQUENCE OF EndptWlanListTableEntry
                MAX-ACCESS    not-accessible
                STATUS        current
                DESCRIPTION   "List of Wi-Fi networks that have been 
               previously connected, which includes those that were:
               - Automatically detected and previously connected,
               - Manually added"
                ::= { endptWIFI 25 }
endptWlanListTableEntry OBJECT-TYPE
                SYNTAX EndptWlanListTableEntry
                MAX-ACCESS    not-accessible
                STATUS        current
                DESCRIPTION   "Entry of the Wlan List Table of the Wi-Fi networks
            that have been previously connected, which includes those that were:
            - Automatically detected and previously connected,
            - Manually added"
                INDEX     { endptWlanListIndex }
                ::= { endptWlanListTable 1 }
EndptWlanListTableEntry     ::= 
                SEQUENCE  {
                    endptWlanListIndex      INTEGER,
                    endptWlanSSID           DisplayString,
--                    endptWlanSECURITY       DisplayString,
                    endptWlanWPA2EEAPMETHOD DisplayString,
                    endptWlanWPA2EEAPPHASE2 DisplayString,
                    endptWlanWPA2EIDENTITY  DisplayString,
                    endptWlanWPA2EANONYMOUSIDENTITY DisplayString,
--                    endptWlanPASSWORD       DisplayString,
                    endptWlanFROMSETTINGSFILE       INTEGER,
                    endptWlanSTORED         INTEGER,
                    endptWlanAVAILABLE      INTEGER,
                    endptWlanCONNECTED      INTEGER
                }
endptWlanListIndex     OBJECT-TYPE
                SYNTAX  INTEGER
                MAX-ACCESS  not-accessible
                STATUS  current
                DESCRIPTION
                    "WLAN list index."
                ::= { endptWlanListTableEntry 1 }
endptWlanSSID OBJECT-TYPE
                SYNTAX      DisplayString (SIZE(1..32))
                MAX-ACCESS  read-only
                STATUS      current
                DESCRIPTION "SSID of WLAN network. 
            String of up to 32 characters"
                ::= { endptWlanListTableEntry 2 }
--endptWlanSECURITY  OBJECT-TYPE
--                SYNTAX      DisplayString (SIZE(1..32))
--                MAX-ACCESS  read-only
--                STATUS      current
--                DESCRIPTION "WLAN Security Standard used: 
--                'none' for no security, 
--                'wep' for WEP security, 
--                'wpa2psk' for WPA2 security with pre-shared key, 
--                'wpapsk' for WPA security wit pre-shared key,  
--                'wpa2e' for WPA2 Enterprise security (802.1x auth.)"
--                ::= { endptWlanListTableEntry 3 }
endptWlanWPA2EEAPMETHOD  OBJECT-TYPE
                SYNTAX      DisplayString (SIZE(1..32))
                MAX-ACCESS  read-only
                STATUS      current
                DESCRIPTION "Pre-configured WPA2 EAP Method for 802.1x authentication of Wi-Fi network. 
                Can be set to: 'PEAP' (Default), 'TLS', 'TTLS', 'PWD'"
                ::= { endptWlanListTableEntry 4 }
endptWlanWPA2EEAPPHASE2  OBJECT-TYPE
                SYNTAX      DisplayString (SIZE(1..32))
                MAX-ACCESS  read-only
                STATUS      current
                DESCRIPTION "Pre-configured WPA2 EAP Phase 2 Method for 802.1x authentication of Wi-Fi network. 
                Can be set to 'none' (Default), 'MSCHAPV2', 'GTC'"
                ::= { endptWlanListTableEntry 5 }
endptWlanWPA2EIDENTITY   OBJECT-TYPE
                SYNTAX      DisplayString (SIZE(1..32))
                MAX-ACCESS  read-only
                STATUS      current
                DESCRIPTION "Pre-configured Identity for 802.1x authentication of Wi-Fi network. 
                1-32 ASCII characters OR empty."
                ::= { endptWlanListTableEntry 6 }
endptWlanWPA2EANONYMOUSIDENTITY   OBJECT-TYPE
                SYNTAX      DisplayString (SIZE(1..32))
                MAX-ACCESS  read-only
                STATUS      current
                DESCRIPTION "Pre-configured anonymous identity for 802.1x authentication of Wi-Fi network. 
                1-32 ASCII characters OR empty."
                ::= { endptWlanListTableEntry 7 }
--endptWlanPASSWORD  OBJECT-TYPE
--                SYNTAX      DisplayString (SIZE(1..64))
--                MAX-ACCESS  read-only
--                STATUS      current
--                DESCRIPTION "Preconfigured Wi-Fi Network Password. 
--                1-64 characters OR empty.
--                Valid characters are A-Z, a-z, 0-9, space, and some other special symbols."
--                ::= { endptWlanListTableEntry 8 }
endptWlanFROMSETTINGSFILE   OBJECT-TYPE
                SYNTAX      INTEGER
                MAX-ACCESS  read-only
                STATUS      current
                DESCRIPTION "Is WLAN network from settings file. 0 - false, 1 - true."
                ::= { endptWlanListTableEntry 9 }
endptWlanSTORED   OBJECT-TYPE
                SYNTAX      INTEGER
                MAX-ACCESS  read-only
                STATUS      current
                DESCRIPTION "Is WLAN network stored. True or False. 0 - false, 1 - true."
                ::= { endptWlanListTableEntry 10 }
endptWlanAVAILABLE   OBJECT-TYPE
                SYNTAX      INTEGER
                MAX-ACCESS  read-only
                STATUS      current
                DESCRIPTION "Is WLAN network available. True or False. 0 - false, 1 - true."
                ::= { endptWlanListTableEntry 11 }
endptWlanCONNECTED   OBJECT-TYPE
                SYNTAX      INTEGER
                MAX-ACCESS  read-only
                STATUS      current
                DESCRIPTION "Is WLAN network in use. True or False. 0 - false, 1 - true."
                ::= { endptWlanListTableEntry 12 }
endptWLANL2PRIORITYFORAUDIO   OBJECT-TYPE
                SYNTAX      INTEGER
                MAX-ACCESS  read-only
                STATUS      current
                DESCRIPTION "For Wi-Fi: specifies the layer 2 priority value for audio frames generated by the telephone.
                Range is 0-7, with a default of 6"
                ::= { endptWIFI 26 }
endptWLANL2PRIORITYFORSIGNALING   OBJECT-TYPE
                SYNTAX      INTEGER
                MAX-ACCESS  read-only
                STATUS      current
                DESCRIPTION "For Wi-Fi: specifies the layer 2 priority value for signaling frames generated by the telephone.
                Range is 0-7, with a default of 3"
                ::= { endptWIFI 27 }
endptWLANDSCPFORAUDIO   OBJECT-TYPE
                SYNTAX      INTEGER
                MAX-ACCESS  read-only
                STATUS      current
                DESCRIPTION "For Wi-Fi: specifies the layer 3 Differentiated Services (DiffServ) Code Point
                for audio frames generated by the telephone.
                Range is 0-63, with a default of 46"
                ::= { endptWIFI 28 }
endptWLANDSCPFORSIGNALING   OBJECT-TYPE
                SYNTAX      INTEGER
                MAX-ACCESS  read-only
                STATUS      current
                DESCRIPTION "For Wi-Fi: specifies the layer 3 Differentiated Services (DiffServ) Code Point
                for signaling frames generated by the telephone.
                Range is 0-63, with a default of 34"
                ::= { endptWIFI 29 }
endptETHERNETCARRIERDETECTED   OBJECT-TYPE
                SYNTAX      INTEGER
                MAX-ACCESS  read-only
                STATUS      current
                DESCRIPTION "For Wi-Fi: 0 - Ethernet carrier not detected
                                        1 - Ethernet carrier detected"
                ::= { endptWIFI 31 }
endptWLANCOUNTRY   OBJECT-TYPE
                SYNTAX      DisplayString
                MAX-ACCESS  read-only
                STATUS      current
                DESCRIPTION "For Wi-Fi: Country code of ISO 3166:
                AR, AU, BR, CA, FR, DE, IE, IT, MX, ES, GB, US, RU"
                ::= { endptWIFI 32 }
endptNETWORKCONFIGMANUAL   OBJECT-TYPE
                SYNTAX      INTEGER
                MAX-ACCESS  read-only
                STATUS      current
                DESCRIPTION "For Wi-Fi: specifies network configuration was set manually or not:
                0 - auto, 1 - manual"
                ::= { endptWIFI 33 }
endptCHANGEOVERETHERNETTOWIFIACTIVE   OBJECT-TYPE
                SYNTAX      INTEGER
                MAX-ACCESS  read-only
                STATUS      current
                DESCRIPTION "For Wi-Fi: specifies detection of change over ethernet to Wi-Fi:
                0 - not active, 1 - active"
                ::= { endptWIFI 34 }
endptWLANENABLE80211D   OBJECT-TYPE
                SYNTAX      INTEGER
                MAX-ACCESS  read-only
                STATUS      current
                DESCRIPTION "For Wi-Fi: specifies enabling 80211d:
                0 - disable, 1 - enable"
                ::= { endptWIFI 35 }
endptENABLENETWORKCONFIGBYUSER   OBJECT-TYPE
                SYNTAX      INTEGER
                MAX-ACCESS  read-only
                STATUS      current
                DESCRIPTION "For Wi-Fi: specifies if network configuration can be modified by the user:
                0 - disable, 1 - enable"
                ::= { endptWIFI 36 }
endptWIFICHIPPRESENT   OBJECT-TYPE
                SYNTAX      INTEGER
                MAX-ACCESS  read-only
                STATUS      current
                DESCRIPTION "For Wi-Fi: specifies if Wi-Fi chip is presented or not:
                0 - not presented, 1 - presented"
                ::= { endptWIFI 37 }
endptREUSEWIFI  OBJECT-TYPE
                SYNTAX      INTEGER
                MAX-ACCESS  read-only
                STATUS      current
                DESCRIPTION "Displays if DHCP failed and previous network parameters are used over Wi-Fi."
                ::= { endptWIFI 38 }
endptREUSEWIFIIPADDRESS     OBJECT-TYPE
                SYNTAX      IpAddress
                MAX-ACCESS  read-only
                STATUS      current
                DESCRIPTION "Endpoint IP address on Wi-Fi. This variable returns a 
                4-octet string specifying the IP address which will be used when DHCP fails over Wi-Fi."
                ::= { endptWIFI 39 }
endptREUSEWIFISUBNETMASK     OBJECT-TYPE
                SYNTAX      IpAddress
                MAX-ACCESS  read-only
                STATUS      current
                DESCRIPTION "Subnet mask. This value will be assigned for Wi-Fi subnet mask parameter when DHCP fails over Wi-Fi."
                ::= { endptWIFI 40 }
endptREUSEWIFIROUTERSLIST     OBJECT-TYPE
                SYNTAX      DisplayString
                MAX-ACCESS  read-only
                STATUS      current
                DESCRIPTION "List of router addresses. This variable returns a sequence of IP addresses, in 
                dotted-decimal format and separated by commas. They will be used to find possible router address when DHCP fails over Wi-Fi."
                ::= { endptWIFI 41 }
endptREUSEWIFIROUTERINUSE     OBJECT-TYPE
                SYNTAX      IpAddress
                MAX-ACCESS  read-only
                STATUS      current
                DESCRIPTION "Router address. This value will be assigned for router in use parameter when DHCP fails over Wi-Fi."
                ::= { endptWIFI 42 }
endptWIFIDEBUGOPAQUESTRING     OBJECT-TYPE
                SYNTAX      DisplayString
                MAX-ACCESS  read-only
                STATUS      current
                DESCRIPTION "Opaque Wi-Fi debug string. To be used only by Wi-Fi Service engineer."
                ::= { endptWIFI 43 }
endptWLANMAXAUTHFAILRETRIES     OBJECT-TYPE
                SYNTAX      INTEGER
                MAX-ACCESS  read-only
                STATUS      current
                DESCRIPTION "Number of Wi-Fi connection retries after authentication failure. Range is 0-4, with a default of 3."
                ::= { endptWIFI 44 }

endptBLUETOOTH   OBJECT IDENTIFIER ::= { avayaSparkMIB 9 }
endptBLUETOOTHSTAT   OBJECT-TYPE
                SYNTAX      INTEGER
                MAX-ACCESS  read-only
                STATUS      current
                DESCRIPTION "For Bluetooth: specifies end user has the ability to connect a Bluetooth headsets 
                to the desk phone or not:
                1 (default value) - means that user has the ability to connect a Bluetooth headsets to the desk phone
                0 - Bluetooth is disabled and the user is not given an option to enable it"
                ::= { endptBLUETOOTH 1 }
endptOPTBLUETOOTH   OBJECT-TYPE
                SYNTAX      INTEGER
                MAX-ACCESS  read-only
                STATUS      current
                DESCRIPTION "For Bluetooth: the Bluetooth option was actually activated or not when the phone is rebooted:
                1 - Bluetooth is enabled by User
                0 - Bluetooth is disabled by User"
                ::= { endptBLUETOOTH 2 }
endptHANDSETTYPE   OBJECT-TYPE
                SYNTAX      INTEGER
                MAX-ACCESS  read-only
                STATUS      current
                DESCRIPTION "For Bluetooth: indicates a type of attached handset:
                1 - means that Cordless Handset has been attached to the phone.
                0 (default value) - means that Wired Handset has been attached to the phone. 
                -1 - Handset device is not attached to the phone"
                ::= { endptBLUETOOTH 3 }

endptDES   OBJECT IDENTIFIER ::= { avayaSparkMIB 10 }
endptDESSTATUS   OBJECT-TYPE
                SYNTAX      INTEGER
                MAX-ACCESS  read-only
                STATUS      current
                DESCRIPTION "Specifies if DES discovery is to be attempted during the boot process if there is no 
		configuration file server provisioned on the phone:
		0 - DES discovery is disabled and can only be restored with Reset to Defaults
		1 - DES discovery is disabled 
		2 - DES discovery is enabled (default)"
                ::= { endptDES 1 }
endptDESBLOCK   OBJECT-TYPE
                SYNTAX      INTEGER
                MAX-ACCESS  read-only
                STATUS      current
                DESCRIPTION "Specifies if DES discovery is allowed to be attempted during the boot process:
		0 - DES discovery is allowed 
		1 - DES discovery will not be attempted. DES can still be triggered from the Admin menu 
		2 - DES discovery is prohibited under all conditions"
                ::= { endptDES 2 }
endptDESACTIVE   OBJECT-TYPE
                SYNTAX      INTEGER
                MAX-ACCESS  read-only
                STATUS      current
                DESCRIPTION "DES Active:
		0 - DES discovery is disabled 
		1 - DES discovery should be initiated if there is no configuration server defined 
		2 - DES discovery must be initiated"
                ::= { endptDES 3 }
endptENABLEPUBLICCACERTS   OBJECT-TYPE
                SYNTAX      INTEGER
                MAX-ACCESS  read-only
                STATUS      current
                DESCRIPTION "Public CA Certs:
                0 - Embedded public CA certs are only trusted when TRUSTCERTS is empty 
		1 - Embedded public CA certs are always trusted"
                ::= { endptDES 4 }
endptDESSUPPORT   OBJECT-TYPE
                SYNTAX      INTEGER
                MAX-ACCESS  read-only
                STATUS      current
                DESCRIPTION "DES Support:
		0 - There is no factory support for DES 
		1 - Factory support for DES is enabled"
                ::= { endptDES 5 }
endptFACTORYCERTSTATUS   OBJECT-TYPE
                SYNTAX      INTEGER
                MAX-ACCESS  read-only
                STATUS      current
                DESCRIPTION "FACTORY Cert Status:
		0 - There is no factory certificate present on the phone 
		1 - A factory certificate is present and it is not expired 
		2 - A factory certificate is present but it is expired"
                ::= { endptDES 6 }
endptFACTORYCERTEXPIRYDATE   OBJECT-TYPE
                SYNTAX      DisplayString
                MAX-ACCESS  read-only
                STATUS      current
                DESCRIPTION "Contains the expiry date of the factory certificate if it exists. The certificate 
		expiry date is in the format DD-MMM-YYYY(e.g. 24-Jan-2028). If there is no factory certificate, 
		the value should be empty."
                ::= { endptDES 7 }

endptWEB   OBJECT IDENTIFIER ::= { avayaSparkMIB 11 }
endptENABLEWEBSERVER   OBJECT-TYPE
                SYNTAX      INTEGER
                MAX-ACCESS  read-only
                STATUS      current
                DESCRIPTION "Enable Web Server:
		0 - Web server is disabled.
		1 - Web server is enabled."
                ::= { endptWEB 1 }
endptWEBHTTPPORT   OBJECT-TYPE
                SYNTAX      INTEGER
                MAX-ACCESS  read-only
                STATUS      current
                DESCRIPTION "Specifies the port on which web server will be accessed using HTTP.
		Default value will be used if not configured or configured blank in settings file."
                ::= { endptWEB 2 }
endptWEBHTTPSPORT   OBJECT-TYPE
                SYNTAX      INTEGER
                MAX-ACCESS  read-only
                STATUS      current
                DESCRIPTION "Specifies the port on which web server will be accessed using HTTPS.
		Default value will be used if not configured or configured blank in settings file."
                ::= { endptWEB 3 }
endptUSECERTIFICATEFORWEBSERVER   OBJECT-TYPE
                SYNTAX      INTEGER
                MAX-ACCESS  read-only
                STATUS      current
                DESCRIPTION "Specifies the certificate to be sent to the client for authentication when 
		TLS connection is requested by the client to the web server:
		0 - use self-signed certificate installed in factory.
		1 - use custom server certificate"
                ::= { endptWEB 4 }
endptIDCERTSWEB   OBJECT-TYPE
                SYNTAX      DisplayString
                MAX-ACCESS  read-only
                STATUS      current
                DESCRIPTION "Manages the uploaded certificate using web i.e display the uploaded certificate 
		filename on web, delete certificate etc. "
                ::= { endptWEB 5 }
endptTRUSTCERTSWEB   OBJECT-TYPE
                SYNTAX      DisplayString
                MAX-ACCESS  read-only
                STATUS      current
                DESCRIPTION "Manages the uploaded certificate using web i.e display the uploaded certificate 
                filename on web, delete certificate etc. "
                ::= { endptWEB 6 }
endptLANGUAGESWEB   OBJECT-TYPE
                SYNTAX      DisplayString
                MAX-ACCESS  read-only
                STATUS      current
                DESCRIPTION "Manages the uploaded language files using web i.e display the uploaded languages
                filename on web, delete language file etc. "
                ::= { endptWEB 7 }
endptWEBSERVERCERT   OBJECT-TYPE
                SYNTAX      DisplayString
                MAX-ACCESS  read-only
                STATUS      current
                DESCRIPTION "Specifies the certificate name which is uploaded for web server"
                ::= { endptWEB 8 }

endptNAT   OBJECT IDENTIFIER ::= { avayaSparkMIB 12 }
endptSTUNSERVERADDRESS   OBJECT-TYPE
                SYNTAX      DisplayString
                MAX-ACCESS  read-only
                STATUS      current
                DESCRIPTION "STUN Server address, in IPv4, IPv6 or FQDN format. When empty, NAT traversal is disabled."
                ::= { endptNAT 1 }
endptSTUNUDPINITIALTIMEOUTMSEC   OBJECT-TYPE
                SYNTAX      INTEGER
                MAX-ACCESS  read-only
                STATUS      current
                DESCRIPTION "Initial timeout, in milliseconds, to wait for a Response to a STUN Request sent over UDP.
                The timeout value is internally doubled after each [re]transmission. 
                Valid values are 500 (1/2 second) through 3000 (3 seconds). The default value is 500."
                ::= { endptNAT 2 }
endptSTUNUDPMAXTRANSMISSIONS   OBJECT-TYPE
                SYNTAX      INTEGER
                MAX-ACCESS  read-only
                STATUS      current
                DESCRIPTION "The number of times the phone will transmit a STUN Request until a Response is received,
                after which the Request will be treated as failed. 
                Valid values are 1 through 7. The default value is 7."
                ::= { endptNAT 3 }
endptSTUNUDPMAXMEDIATRANSMISSIONS   OBJECT-TYPE
                SYNTAX      INTEGER
                MAX-ACCESS  read-only
                STATUS      current
                DESCRIPTION "The number of times the phone will transmit a STUN Request to get NAT bindings for the phone's
                RTP/RTCP IP address and ports. Retransmissions continue until a response is received, or 
                until a total number of requests have been sent.
                Valid values are 1 through 4. The default value is 3."
                ::= { endptNAT 4 }
endptNATSIGNALINGKEEPALIVEENABLED   OBJECT-TYPE
                SYNTAX      INTEGER
                MAX-ACCESS  read-only
                STATUS      current
                DESCRIPTION "Disable keep-alives and ping/pong connectivity checking for all SIP registrations.
                  Value - Operation
                    0 - Disable keep-alives for SIP signaling flow
                    1 - Enable keep-alives for SIP signaling flow (default)"
                ::= { endptNAT 5 }		
endptNATSIGNALINGKEEPALIVEOVERRIDESEC   OBJECT-TYPE
                SYNTAX      INTEGER
                MAX-ACCESS  read-only
                STATUS      current
                DESCRIPTION "Override of the automatically-computed maximum interval, in seconds, between keep-alives
                (STUN messages for UDP, double-CRLFs for TCP/TLS) to (a) Refresh NAT bindings for the phone's signaling
                IP address and port, and (b) Optionally perform ping/pong checking.
                Valid values are 15 through 900 (15 minutes). The default value is 29.
                  Value - Operation
                  15-900 - The phone will unconditionally use this value as the keep-alive interval for every SIP registration and dialog"
                ::= { endptNAT 6 }
endptNATMEDIAKEEPALIVEENABLED   OBJECT-TYPE
                SYNTAX      INTEGER
                MAX-ACCESS  read-only
                STATUS      current
                DESCRIPTION "Disable keep-alives and ping/pong connectivity checking for RTP/RTCP flow.
                  Value - Operation
                    0 - Disable keep-alives for RTP/RTCP flow
                    1 - Enable keep-alives for RTP/RTCP flow (default)"
                ::= { endptNAT 7 }		
endptNATMEDIAKEEPALIVESEC   OBJECT-TYPE
                SYNTAX      INTEGER
                MAX-ACCESS  read-only
                STATUS      current
                DESCRIPTION "Maximum interval, in seconds, between STUN keep-alives to refresh NAT bindings for the phone's
                RTP and RTCP IP address and ports.
                Valid values are 15 through 900 (15 minutes). The default value is 15 seconds.
                  Value - Operation
                  15-900 - The phone will use this value as the keep-alive interval for RTP and RTCP"
                ::= { endptNAT 8 }
--NAT_TBD: Future
--endptNATENABLESIGNALINGFLOWCHECK  OBJECT-TYPE
--                SYNTAX      INTEGER
--                MAX-ACCESS  read-only
--                STATUS      current
--                DESCRIPTION "Enable ping/pong flow checking with NAT keep-alives for signaling (STUN Binding Request/Response over UDP,
--                or double-CRLF/single-CRLF over TCP/TLS) to detect (a) A changed public signaling IP address or port mapping due to a
--                NAT reboot, or (b) A signaling flow failure due to a proxy crash. Flow checking should NOT be enabled unless pong responses
--                are known to be guaranteed. Otherwise, the phone may incorrectly assume that a given registration or dialog flow is dead.
--                  Value - Operation
--                    0 - Disable checking for pong responses (default)
--                    1 - Enable checking for pong responses"
--                ::= { endptNAT 9 }

endptBLF   OBJECT IDENTIFIER ::= { avayaSparkMIB 13 }
endptBLFLISTURI  OBJECT-TYPE
                SYNTAX      DisplayString
                MAX-ACCESS  read-only
                STATUS      current
                DESCRIPTION "Specifies the BLF list URI which should be used for subscription to 'Dialog' event package."
                ::= { endptBLF 1 }
endptCALLPICKUPFAC  OBJECT-TYPE
                SYNTAX      DisplayString
                MAX-ACCESS  read-only
                STATUS      current
                DESCRIPTION "Specifies the feature access code which will be inserted in INVITE message to perform Call Pickup operation.
                The default value is '*97'"
                ::= { endptBLF 2 }
endptCALLPICKUPBARGEINFAC  OBJECT-TYPE
                SYNTAX      DisplayString
                MAX-ACCESS  read-only
                STATUS      current
                DESCRIPTION "Specifies the feature access code which will be inserted in INVITE message to perform Barge-in operation.
                The default value is '*33'"
                ::= { endptBLF 3 }
endptCALLUNPARKFAC  OBJECT-TYPE
                SYNTAX      DisplayString
                MAX-ACCESS  read-only
                STATUS      current
                DESCRIPTION "Specifies the feature access code which will be inserted in INVITE message to perform Call Park Retrieve operation.
                The default value is '*88'"
                ::= { endptBLF 4 }
endptBLFINCOMINGCALLINDICATION  OBJECT-TYPE
                SYNTAX      INTEGER
                MAX-ACCESS  read-only
                STATUS      current
                DESCRIPTION "Specifies the indication of BLF incoming calls.
                  Value - Operation
                    0 - None (no alerting for BLF incoming call)
                    1 - Audible (only audible alerting for BLF incoming call)
                    2 - Visual (only visual alerting for BLF incoming call)
                    3 - Default (the behavior based on BLF_INCOMING_CALL_INDICATION_MODE parameter value)
                    4 - Both (both audible and visual alerting for BLF incoming call)"
                ::= { endptBLF 5 }
endptBLFPARKEDCALLINDICATION  OBJECT-TYPE
                SYNTAX      INTEGER
                MAX-ACCESS  read-only
                STATUS      current
                DESCRIPTION "Specifies the indication of BLF parked calls.
                  Value - Operation
                    0 - None (no alerting for BLF parked call)
                    1 - Default (the behavior based on BLF_PARKED_CALL_INDICATION_MODE parameter value)
                    2 - Visual (only visual alerting for BLF parked call)
                    3 - Both (both audible and visual alerting for BLF parked call)
                    4 - Audible (only audible alerting for BLF parked call)"
                ::= { endptBLF 6 }

endptALLOWBLFLISTCHANGE  OBJECT-TYPE
                SYNTAX      INTEGER
                MAX-ACCESS  read-only
                STATUS      current
                DESCRIPTION "Specifies the permissions to add/delete BLF line keys.
                  Value - Operation
                    0 - User is not allowed to add/delete BLF monitored users
                    1 - User is allowed only to delete BLF monitored users
                    2 - User is allowed only to add BLF monitored users
                    3 - User is allowed to add and delete BLF monitored users (default)"
                ::= { endptBLF 7 }

endptBLFPICKUPRINGTYPE  OBJECT-TYPE
                SYNTAX      DisplayString
                MAX-ACCESS  read-only
                STATUS      current
                DESCRIPTION "Defines the ringtone that will be played when BLF monitored user has an incoming call. 
                Applicable only if BLF_ PICKUP_INDICATION requires audible indication."
                ::= { endptBLF 8 }

endptBLFPARKRINGTYPE  OBJECT-TYPE
                SYNTAX      DisplayString
                MAX-ACCESS  read-only
                STATUS      current
                DESCRIPTION "Defines the ringtone that will be played when BLF monitored user has a parked call. 
                Applicable only if BLF_ CALL_PARK_INDICATION requires audible indication."
                ::= { endptBLF 9 }

endptBLFINCOMINGCALLINDICATIONMODE  OBJECT-TYPE
                SYNTAX      INTEGER
                MAX-ACCESS  read-only
                STATUS      current
                DESCRIPTION "Specifies the mode for indication for BLF incoming call.
                  Value - Operation
                    0 - None (no alerting for BLF incoming call)
                    1 - Audible (only audible alerting for BLF incoming call)
                    2 - Visual (only visual alerting for BLF incoming call)
                    3 - Both (default - both audible and visual alerting for BLF incoming call)
                    4 - Force None (no alerting for BLF incoming call)
                    5 - Force Audible (forced only audible alerting for BLF incoming call)
                    6 - Force Visual (forced only visual alerting for BLF incoming call)
                    7 - Force Both (forced both audible and visual alerting for BLF incoming call)"
                ::= { endptBLF 10 }

endptBLFPARKEDCALLINDICATIONMODE  OBJECT-TYPE
                SYNTAX      INTEGER
                MAX-ACCESS  read-only
                STATUS      current
                DESCRIPTION "Specifies the mode for indication for BLF parked call.
                  Value - Operation
                    0 - None (no alerting for BLF parked call)
                    1 - Audible (only audible alerting for BLF parked call)
                    2 - Visual (only visual alerting for BLF parked call)
                    3 - Both (both audible and visual alerting for BLF parked call)
                    4 - Force None (no alerting for BLF incoming call)
                    5 - Force Audible (forced only audible alerting for BLF parked call)
                    6 - Force Visual (forced only visual alerting for BLF parked call)
                    7 - Force Both (forced both audible and visual alerting for BLF parked call)"
                ::= { endptBLF 11 }
                
endptBLFPICKUPMETHOD  OBJECT-TYPE
                SYNTAX      INTEGER
                MAX-ACCESS  read-only
                STATUS      current
                DESCRIPTION "Specifies which method will be used to pickup the BLF call
		  Value - Operation:
		    0 - Pickup BLF call using Invite with FAC in Request URI (Default)
		    1 - Pickup BLF call using Invite with Replaces header"
                ::= { endptBLF 12 }

endptBLFSHORTFORMUSERID  OBJECT-TYPE
                SYNTAX      DisplayString
                MAX-ACCESS  read-only
                STATUS      current
                DESCRIPTION "Aura legacy usage.
                    Extended for RingCentral to identify if an incoming BLF notify with RingCentral extension is from itself. If yes, 
                    suppress the alerting and only present outbound call."
                ::= { endptBLF 13 }

endptBroadWorks   OBJECT IDENTIFIER ::= { avayaSparkMIB 14 }

endptBROADWORKSANYWHEREAVAILABLE  OBJECT-TYPE
                SYNTAX      INTEGER
                MAX-ACCESS  read-only
                STATUS      current
                DESCRIPTION "Is BroadWorks Anywhere feature available. 0 - False, 1 - True."
                ::= { endptBroadWorks 1 }

endptBROADWORKSMOBILITYAVAILABLE  OBJECT-TYPE
                SYNTAX      INTEGER
                MAX-ACCESS  read-only
                STATUS      current
                DESCRIPTION "Is BroadWorks Mobility feature available. 0 - False, 1 - True."
                ::= { endptBroadWorks 2 }

endptBROADWORKSEXECUTIVEAVAILABLE  OBJECT-TYPE
                SYNTAX      INTEGER
                MAX-ACCESS  read-only
                STATUS      current
                DESCRIPTION "Is BroadWorks Executive feature available. 0 - False, 1 - True."
                ::= { endptBroadWorks 3 }

endptBROADWORKSEXECUTIVEASSISTANTAVAILABLE  OBJECT-TYPE
                SYNTAX      INTEGER
                MAX-ACCESS  read-only
                STATUS      current
                DESCRIPTION "Is BroadWorks Executive Assistant feature available. 0 - False, 1 - True."
                ::= { endptBroadWorks 4 }

endptBROADWORKSCALLFWDALWAYSAVAILABLE  OBJECT-TYPE
                SYNTAX      INTEGER
                MAX-ACCESS  read-only
                STATUS      current
                DESCRIPTION "Is BroadWorks Call Forward Always feature available. 0 - False, 1 - True."
                ::= { endptBroadWorks 5 }

endptBROADWORKSCALLFWDNOANSWERAVAILABLE  OBJECT-TYPE
                SYNTAX      INTEGER
                MAX-ACCESS  read-only
                STATUS      current
                DESCRIPTION "Is BroadWorks Call Forward No Answer feature available. 0 - False, 1 - True."
                ::= { endptBroadWorks 6 }

endptBROADWORKSDONOTDISTURBAVAILABLE  OBJECT-TYPE
                SYNTAX      INTEGER
                MAX-ACCESS  read-only
                STATUS      current
                DESCRIPTION "Is BroadWorks Do Not Disturb feature available. 0 - False, 1 - True."
                ::= { endptBroadWorks 7 }

endptBROADWORKSSIMULTANEOUSRINGAVAILABLE  OBJECT-TYPE
                SYNTAX      INTEGER
                MAX-ACCESS  read-only
                STATUS      current
                DESCRIPTION "Is BroadWorks Simultaneous Ring available. 0 - False, 1 - True."
                ::= { endptBroadWorks 8 }

endptBROADWORKSCALLPARKAVAILABLE  OBJECT-TYPE
                SYNTAX      INTEGER
                MAX-ACCESS  read-only
                STATUS      current
                DESCRIPTION "Is BroadWorks Call Park available. 0 - False, 1 - True."
                ::= { endptBroadWorks 9 }

endptBROADWORKSXSIURL  OBJECT-TYPE
                SYNTAX      DisplayString
                MAX-ACCESS  read-only
                STATUS      current
                DESCRIPTION "URL of BroadWorks XSP server"
                ::= { endptBroadWorks 10 }

endptBROADWORKSXSIHEARTBEAT  OBJECT-TYPE
                SYNTAX      INTEGER
                MAX-ACCESS  read-only
                STATUS      current
                DESCRIPTION "XSI event channel heart beat. Default value: 15, min: 1, max: 999."
                ::= { endptBroadWorks 11 }

endptBROADWORKSXSISTATE  OBJECT-TYPE
                SYNTAX      INTEGER
                MAX-ACCESS  read-only
                STATUS      current
                DESCRIPTION "Indicates XSI state. Values: 0 - XSI initializing (default), 1 - XSI running, 2 - XSI failed"
                ::= { endptBroadWorks 12 }

endptBROADWORKSXSIEVENTCHANNELDURATION  OBJECT-TYPE
                SYNTAX      INTEGER
                MAX-ACCESS  read-only
                STATUS      current
                DESCRIPTION "Defines the time duration in minutes for XSI event channel, i.e. phone will ask XSP server 
                to maintain the established Comet HTTP connection for the specified period of time. 
                After 50% of this time phone will reestablish Comet HTTP connection."
                ::= { endptBroadWorks 13 }

endptBROADWORKSXSIUSERID  OBJECT-TYPE
                SYNTAX      DisplayString
                MAX-ACCESS  read-only
                STATUS      current
                DESCRIPTION "Specifies the Broadsoft's User Id which phone should use for XSI athentication (SIP or Web methods).
                Note: it is User Id without @ and domain"
                ::= { endptBroadWorks 14 }

endpt3PCCSERVERMODE  OBJECT-TYPE
                SYNTAX      INTEGER
                MAX-ACCESS  read-only
                STATUS      current
                DESCRIPTION "When a 3PCC environment is enabled using ENABLE_3PCC_ENVIRONMENT=1,
                this setting defines if the phone expects a generic 3PCC server or a Broadsoft server
                  Value - Operation
                    0 - Generic
                    1 - Broadsoft
                    2 - 3CX
                    3 - Netsapiens
                    4 - RingCentral (no J129)
                    5 - Avaya Cloud (no J129)"
                ::= { endptBroadWorks 15 }

endptWAITFORCALLOPERATIONRESPONSE  OBJECT-TYPE
                SYNTAX      INTEGER
                MAX-ACCESS  read-only
                STATUS      current
                DESCRIPTION "Specifies the time in seconds before providing a response for user initiated call operation. 
                This parameter is applicable to all server environments (Aura/ 3PCC/IP Office)
                Example:
                User goes off-hook (phone sends an invite. If there is no response from the proxy for 3 seconds
                (assume default value), it will result in auinotification."
                ::= { endptBroadWorks 16 }

endptBWENABLEDIR  OBJECT-TYPE
                SYNTAX      INTEGER
                MAX-ACCESS  read-only
                STATUS      current
                DESCRIPTION "Specifies BroadWorks Directory feature availability state.
                  Value - Operation
                    0 - disable
                    1 - enable"
                ::= { endptBroadWorks 17 }

endptBWENABLEDIRENTERPRISE  OBJECT-TYPE
                SYNTAX      INTEGER
                MAX-ACCESS  read-only
                STATUS      current
                DESCRIPTION "Specifies BroadWorks Enterprise directory availability state.
                  Value - Operation
                    0 - disable
                    1 - enable"
                ::= { endptBroadWorks 18 }

endptBWENABLEDIRENTERPRISECOMMON  OBJECT-TYPE
                SYNTAX      INTEGER
                MAX-ACCESS  read-only
                STATUS      current
                DESCRIPTION ""
                ::= { endptBroadWorks 19 }

endptBWENABLEDIRGROUP  OBJECT-TYPE
                SYNTAX      INTEGER
                MAX-ACCESS  read-only
                STATUS      current
                DESCRIPTION "Specifies BroadWorks Group directory availability state.
                  Value - Operation
                    0 - disable
                    1 - enable"
                ::= { endptBroadWorks 20 }

endptBWENABLEDIRGROUPCOMMON  OBJECT-TYPE
                SYNTAX      INTEGER
                MAX-ACCESS  read-only
                STATUS      current
                DESCRIPTION "Specifies BroadWorks Group Common directory availability state.
                  Value - Operation
                    0 - disable
                    1 - enable"
                ::= { endptBroadWorks 21 }

endptBWENABLEDIRPERSONAL  OBJECT-TYPE
                SYNTAX      INTEGER
                MAX-ACCESS  read-only
                STATUS      current
                DESCRIPTION "Specifies BroadWorks Personal directory availability state.
                  Value - Operation
                    0 - disable
                    1 - enable"
                ::= { endptBroadWorks 22 }

endptBWENABLEDIRCUSTOM  OBJECT-TYPE
                SYNTAX      INTEGER
                MAX-ACCESS  read-only
                STATUS      current
                DESCRIPTION "Specifies BroadWorks Custom directory availability state.
                  Value - Operation
                    0 - disable
                    1 - enable"
                ::= { endptBroadWorks 23 }

endptBWDIRENTERPRISEDESCRIPTION  OBJECT-TYPE
                SYNTAX      DisplayString
                MAX-ACCESS  read-only
                STATUS      current
                DESCRIPTION "The display name for BroadWorks Enterprise directory."
                ::= { endptBroadWorks 24 }

endptBWDIRENTERPRISECOMMONDESCRIPTION  OBJECT-TYPE
                SYNTAX      DisplayString
                MAX-ACCESS  read-only
                STATUS      current
                DESCRIPTION "The display name for BroadWorks Enterprise Common directory."
                ::= { endptBroadWorks 25 }

endptBWDIRGROUPDESCRIPTION  OBJECT-TYPE
                SYNTAX      DisplayString
                MAX-ACCESS  read-only
                STATUS      current
                DESCRIPTION "The display name for BroadWorks Group directory."
                ::= { endptBroadWorks 26 }

endptBWDIRGROUPCOMMONDESCRIPTION  OBJECT-TYPE
                SYNTAX      DisplayString
                MAX-ACCESS  read-only
                STATUS      current
                DESCRIPTION "The display name for BroadWorks Group Common directory."
                ::= { endptBroadWorks 27 }

endptBWDIRPERSONALDESCRIPTION  OBJECT-TYPE
                SYNTAX      DisplayString
                MAX-ACCESS  read-only
                STATUS      current
                DESCRIPTION "The display name for BroadWorks Personal directory."
                ::= { endptBroadWorks 28 }

endptBWDIRCUSTOMDESCRIPTION  OBJECT-TYPE
                SYNTAX      DisplayString
                MAX-ACCESS  read-only
                STATUS      current
                DESCRIPTION "The display name for BroadWorks Custom directory."
                ::= { endptBroadWorks 29 }

endptBWDIRENTERPRISEEXTENSION  OBJECT-TYPE
                SYNTAX      DisplayString
                MAX-ACCESS  read-only
                STATUS      current
                DESCRIPTION "The display name for BroadWorks Enterprise directory extension."
                ::= { endptBroadWorks 30 }

endptBWDIRENTERPRISECOMMONEXTENSION  OBJECT-TYPE
                SYNTAX      DisplayString
                MAX-ACCESS  read-only
                STATUS      current
                DESCRIPTION "The display name for BroadWorks Enterprise Common directory extension."
                ::= { endptBroadWorks 31 }

endptBWDIRGROUPEXTENSION  OBJECT-TYPE
                SYNTAX      DisplayString
                MAX-ACCESS  read-only
                STATUS      current
                DESCRIPTION "The display name for BroadWorks Group directory extension."
                ::= { endptBroadWorks 32 }

endptBWDIRGROUPCOMMONEXTENSION  OBJECT-TYPE
                SYNTAX      DisplayString
                MAX-ACCESS  read-only
                STATUS      current
                DESCRIPTION "The display name for BroadWorks Group Common directory extension."
                ::= { endptBroadWorks 33 }

endptBWDIRPERSONALEXTENSION  OBJECT-TYPE
                SYNTAX      DisplayString
                MAX-ACCESS  read-only
                STATUS      current
                DESCRIPTION "The display name for BroadWorks Personal directory extension."
                ::= { endptBroadWorks 34 }

endptBWDIRCUSTOMEXTENSION  OBJECT-TYPE
                SYNTAX      DisplayString
                MAX-ACCESS  read-only
                STATUS      current
                DESCRIPTION "The display name for BroadWorks Custom directory extension."
                ::= { endptBroadWorks 35 }

endptCALLPARKINDICATION  OBJECT-TYPE
                SYNTAX      INTEGER
                MAX-ACCESS  read-only
                STATUS      current
                DESCRIPTION "Call park indication parameter will determine how phone will inform user about parked calls in addition to winking Beacon LED.
                  Value - Operation
                    0 - no additional indication
                    1 - audible indication
                    2 - visual indication (on Incoming call screen)
                    3 - audible and visual indication"
                ::= { endptBroadWorks 36 }

endptBWPRIORITYALERTRINGTYPE  OBJECT-TYPE
                SYNTAX      DisplayString
                MAX-ACCESS  read-only
                STATUS      current
                DESCRIPTION "Defines the ringtone that will be played when there is an Broadsoft incoming priority call (Bellcore-dr2)."
                ::= { endptBroadWorks 37 }

endptBWALTERNATENUBMER1ALERTRINGTYPE  OBJECT-TYPE
                SYNTAX      DisplayString
                MAX-ACCESS  read-only
                STATUS      current
                DESCRIPTION "Defines the ringtone that will be played when there is an Broadsoft incoming alternate number 1 call (Bellcore-dr3)."
                ::= { endptBroadWorks 38 }

endptBWALTERNATENUMBER2ALERTRINGTYPE  OBJECT-TYPE
                SYNTAX      DisplayString
                MAX-ACCESS  read-only
                STATUS      current
                DESCRIPTION "Defines the ringtone that will be played when there is an Broadsoft incoming alternate number 2 call (Bellcore-dr4)."
                ::= { endptBroadWorks 39 }

endptCALLDECLINEPOLICY  OBJECT-TYPE
                SYNTAX      INTEGER
                MAX-ACCESS  read-only
                STATUS      current
                DESCRIPTION "Indicates a decline method of the feature"
                ::= { endptBroadWorks 40 }

endptBWHOTELINGMODE   OBJECT-TYPE
               SYNTAX      INTEGER
               MAX-ACCESS  read-only
               STATUS      current
               DESCRIPTION "
                       Defines primary or guest location for flexible seating.
                       1 - if the device profile is the primary location of a user and this user has the Hoteling Host service assigned
                       2 - if the device profile is the primary location of a Flexible Seating Host virtual subscriber
                       3 - if the device profile is the Flexible Seating location of a guest
                       0 - if none of the above is true"
               ::= { endptBroadWorks 41 }

endptBSCCENABLED  OBJECT-TYPE
                SYNTAX      INTEGER
                MAX-ACCESS  read-only
                STATUS      current
                DESCRIPTION "Defines that Broadsoft Call Center is available in the settings file."
                ::= { endptBroadWorks 42 }

endptBSCCACTIVE  OBJECT-TYPE
                SYNTAX      INTEGER
                MAX-ACCESS  read-only
                STATUS      current
                DESCRIPTION "Defines that Broadsoft Call Center is available according to the xsi settings."
                ::= { endptBroadWorks 43 }

endptBSCCUNAVAILCODES  OBJECT-TYPE
                SYNTAX      DisplayString
                MAX-ACCESS  read-only
                STATUS      current
                DESCRIPTION "Specifies Broadsoft Call Center agent's unavailability reason code."
                ::= { endptBroadWorks 44 }

endptBSCCDISPCODES  OBJECT-TYPE
                SYNTAX      DisplayString
                MAX-ACCESS  read-only
                STATUS      current
                DESCRIPTION "Specifies Broadsoft Call Center list of disposition codes."
                ::= { endptBroadWorks 45 }

endptBSCCSUPERVISORS  OBJECT-TYPE
                SYNTAX      DisplayString
                MAX-ACCESS  read-only
                STATUS      current
                DESCRIPTION "Specifies Broadsoft Call Center list of supervisors."
                ::= { endptBroadWorks 46 }

endptBSCCCOTENABLED  OBJECT-TYPE
                SYNTAX      INTEGER
                MAX-ACCESS  read-only
                STATUS      current
                DESCRIPTION "Specifies Broadsoft Call Center Customer Originated Trace is enabled."
                ::= { endptBroadWorks 47 }

endptBSCCAUTOMATICSTATE  OBJECT-TYPE
                SYNTAX      INTEGER
                MAX-ACCESS  read-only
                STATUS      current
                DESCRIPTION "Specifies if the phone should automatically set state Sign-In and Sign-Out on login and logout, respectively."
                ::= { endptBroadWorks 48 }

endptESCALATIONFAC  OBJECT-TYPE
                SYNTAX      DisplayString
                MAX-ACCESS  read-only
                STATUS      current
                DESCRIPTION "Specifies FAC that can be used by the phone to invoke Escalation."
                ::= { endptBroadWorks 49 }

endptPNP   OBJECT IDENTIFIER ::= { avayaSparkMIB 15 }

endptPNPENABLED  OBJECT-TYPE
                SYNTAX      INTEGER
                MAX-ACCESS  read-only
                STATUS      current
                DESCRIPTION "Specifies if PnP is enabled or not. This value does not define if it is to be activated or not but only defines if PnP can be activated. 0: PnP is disabled, 1: PnP is enabled"
                ::= { endptPNP 1 }

endptPNPACTIVE  OBJECT-TYPE
                SYNTAX      INTEGER
                MAX-ACCESS  read-only
                STATUS      current
                DESCRIPTION "Specifies if PnP is active or not for the current boot. 0: PnP is inactive, 1: PnP activation is allowed"
                ::= { endptPNP 2 }

endptPNPSTATUS  OBJECT-TYPE
                SYNTAX      INTEGER
                MAX-ACCESS  read-only
                STATUS      current
                DESCRIPTION "The current state of PnP if it is currently in progress or the result of PnP if PnP was performed and is complete. This value has no meaning If PnP has been disabled for any reason. 0: PnP is not active, 1: PnP discovery is active, 2: PnP configuration is active, 3: PnP completed successfully, 4: PnP discovery failed, 5: PnP discovery timed out, 6: PnP configuration failed"
                ::= { endptPNP 3 }

endptTR87   OBJECT IDENTIFIER ::= { avayaSparkMIB 16 }

endptTR87SESSIONACTIVE  OBJECT-TYPE
                SYNTAX      INTEGER
                MAX-ACCESS  read-only
                STATUS      current
                DESCRIPTION "Indicates if TR87 session is active: 0 - TR87 session is inactive (default), 1 - TR87 session is active."
                ::= { endptTR87 1 }

END
